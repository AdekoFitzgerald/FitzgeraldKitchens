(setq _KSets_AlternativeASufixList (list "D1"))
(setq _KSets_AlternativeBSufixList (list "C1" "C2"))
(setq _KSets_typeAList (list "A" "C" "D" "E" "H" "L" "M" "R" "S" "Z"))
(setq _KSets_typeBList (list "B" "K" "J" "F" "T"))
(setq _KSets_VariableModelName nil)



;FITZGERALD DOORS
;__________________________________________________________________________________________________________________________________________________________
;__________________________________________________________________________________________________________________________________________________________
(defun PLAIN18_AKANATSETS(x z)
	(setq doorFlags::p2cDoorSource "(list \"##\" 18)")
	(setq doorFlags::p2cEdges (list PvcKoduKAPAK PvcKoduKAPAK PvcKoduKAPAK PvcKoduKAPAK)) 
	(setq doorFlags::p2cFrameThick 55)
)
(mapcar '(lambda (x) (set (read (strcat "PLAIN18" "_" x "KANATSETS")) DUZKPK_AKANATSETS) ) _KSets_typeAList)

(defun PLAIN22_AKANATSETS(x z)
	(setq doorFlags::p2cDoorSource "(list \"##\" 22)")
	(setq doorFlags::p2cEdges (list nil nil nil nil)) 
	(setq doorFlags::p2cFrameThick 55)
)
(mapcar '(lambda (x) (set (read (strcat "PLAIN22" "_" x "KANATSETS")) DUZKPK_AKANATSETS) ) _KSets_typeAList)

(defun SHAKER25_AKANATSETS(x z)
	(setq doorFlags::p2cDoorSource "(list \"##\" 22)")
	(setq doorFlags::p2cEdges (list nil nil nil nil)) 
	(setq doorFlags::p2cFrameThick 55)
)
(mapcar '(lambda (x) (set (read (strcat "SHAKER25" "_" x "KANATSETS")) DUZKPK_AKANATSETS) ) _KSets_typeAList)

(defun SHAKER50_AKANATSETS(x z)
	(setq doorFlags::p2cDoorSource "(list \"##\" 22)")
	(setq doorFlags::p2cEdges (list nil nil nil nil)) 
	(setq doorFlags::p2cFrameThick 55)
)
(mapcar '(lambda (x) (set (read (strcat "SHAKER50" "_" x "KANATSETS")) DUZKPK_AKANATSETS) ) _KSets_typeAList)



;ADEKO KAPAKLARI
;__________________________________________________________________________________________________________________________________________________________
;__________________________________________________________________________________________________________________________________________________________

(defun A17ALU_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "A17ALU" "_" x "KANATSETS")) A17ALU_AKANATSETS) ) _KSets_typeAList)

(defun A17ALU_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "A17ALU" "_" x "KANATSETS")) A17ALU_BKANATSETS) ) _KSets_typeBList)
(mapcar '(lambda (x) (set (read (strcat "A17ALU" "_" x "_MAT_LAYER")) "ALUMINIUM_FRAME") ) _KSets_typeBList)

;__________________________________________________________________________________________________________________________________________________________

(defun A17DUZ_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "A17DUZ" "_" x "KANATSETS")) A17DUZ_AKANATSETS) ) _KSets_typeAList)

(defun A17DUZ_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "A17DUZ" "_" x "KANATSETS")) A17DUZ_BKANATSETS) ) _KSets_typeBList)

;__________________________________________________________________________________________________________________________________________________________

(defun DUZKPK_AKANATSETS(x z)
	(setq doorFlags::p2cDoorSource "INSOURCE")
	(setq doorFlags::p2cFrameThick 55)
)
(mapcar '(lambda (x) (set (read (strcat "DUZKPK" "_" x "KANATSETS")) DUZKPK_AKANATSETS) ) _KSets_typeAList)

(defun DUZKPK_BKANATSETS(x z)
	(setq doorFlags::p2cDoorSource "INSOURCE")
	(setq doorFlags::p2cFrameThick 55)
)
(mapcar '(lambda (x) (set (read (strcat "DUZKPK" "_" x "KANATSETS")) DUZKPK_BKANATSETS) ) _KSets_typeBList)

;__________________________________________________________________________________________________________________________________________________________

;duru model prepared as a spesific example. plain door and frame door configured seperatly because DURU model has been written seperatly for AKanat and BKanat in DURU.kpk
;duru kapak modeli ozel ornek olarak hazirlandi. DURU kapak modeli, DURU.kpk icinde AKanat ve BKanat ayri hazirlanmis. Sets olarak da ayri yazılabilir.
(defun DURU_AKANATSETS(x z) ;Akanat sets ayri
	;(setq doorFlags::p2cDoorSource "INSOURCE")					;send Door to manufacture = "INSOURCE"
	(setq doorFlags::p2cDoorSource "(list \"##\" 20.0)")		;send string door material to manufacture with wildcard ## material name and 20.0 mm thickness
	(setq doorFlags::p2cEdges (list nil nil nil nil))           ;edge band = (list 1top 2right 3below 4left)
	(setq doorFlags::p2cProfiles (list nil nil nil nil))        ;edge profile = (list 1top 2right 3below 4left)
	(setq doorFlags::p2cProfileHandles (list nil nil nil nil))  ;edge handle = (list 1top 2right 3below 4left)
	(setq doorFlags::p2cFrameThick 55.0)                        ;edge frame distance
	(setq doorFlags::p2cSpcRcp 1)                               ;refer to special door recipe = 1
)
(mapcar '(lambda (x) (set (read (strcat "DURU" "_" x "KANATSETS")) DURU_AKANATSETS) ) _KSets_typeAList)

(defun DURU_BKANATSETS(x z) ;Bkanat sets ayri
	;(setq doorFlags::p2cDoorSource "INSOURCE")					;kapak imalata gisin = "INSOURCE"
	(setq doorFlags::p2cDoorSource "##")						;send string door material to manufacture with wildcard ## material name 
	(setq doorFlags::p2cEdges (list nil nil nil nil))			;kenar bant = (list 1ust 2sag 3alt 4sol)
	(setq doorFlags::p2cProfiles (list nil nil nil nil))		;kenar profil = (list 1ust 2sag 3alt 4sol)
	(setq doorFlags::p2cProfileHandles (list nil nil nil nil))	;kenar kulp = (list 1ust 2sag 3alt 4sol)
	(setq doorFlags::p2cFrameThick 55.0)						;kenar cerceve mesafesi
	(setq doorFlags::p2cSpcRcp 1)								;kapak ozel recetesi var = 1
)
;hangi kanatlar Bkanatsets olmalı diye X yerine kanat tipi "B" "K" "J" "F" "T" gelir
;which type of doors should be Bkanatsets is set for x as "B" "K" "J" "F" "T" types
(mapcar '(lambda (x) (set (read (strcat "DURU" "_" x "KANATSETS")) DURU_BKANATSETS) ) _KSets_typeBList)
;kapak alu cerceveli ise modüller hesaplanırken malzeme ismini dwg'deki "ALUMINIUM_FRAME" katmanindan alir. Sadece "B" "K" "J" "F" "T" kanatlar ise arar.
;if door has alu frame, read layer name "ALUMINIUM_FRAME" for material and set for x as "B" "K" "J" "F" "T" types
(mapcar '(lambda (x) (set (read (strcat "DURU" "_" x "_MAT_LAYER")) "ALUMINIUM_FRAME") ) _KSets_typeBList)
;kapak cam katmanı farklı ise cam malzemesini "CAB_DOOR_GLASS" for material katmanindan alir. Sadece "B" "K" "J" "F" "T" kanatlar ise arar.
;if door has glass panel, read layer name "CAB_DOOR_GLASS" and set for x as "B" "K" "J" "F" "T" types
(mapcar '(lambda (x) (set (read (strcat "DURU" "_" x "_GLASS_MAT_LAYER")) "CAB_DOOR_GLASS") ) _KSets_typeBList)

(defun PostRun.Duru_A () ;bkz ulibFormulLabour.lsp
	(post.itag (list "DuruKapakMontaj" (ifnull areaOfDoor.PARENT 0.0) "m2"))
	(post.kapPaKes (list "DuruFolyo" (- pnlW.parent 3) (- pnlH.parent 3) 1.0 pnlMat.Parent pnlRot.Parent))
)

;__________________________________________________________________________________________________________________________________________________________

;alternatif olarak kapak modeli isimleri değişkene bağlanıp dinamik olarak bu şekilde de setlenebilir
;alternatively this can be done like this dynamicly with the help of model name variable
(setq _KSets_VariableModelName "MODELISMI") ;model ismi
	(set (read (strcat _KSets_VariableModelName "_AKANATSETS")) '((x z) ;akanat
		;(setq doorFlags::p2cDoorSource "INSOURCE")
		(setq doorFlags::p2cDoorSource "SANAL_##")
		(setq doorFlags::p2cEdges (list PvcKoduKAPAK PvcKoduKAPAK PvcKoduKAPAK PvcKoduKAPAK) )          
		(setq doorFlags::p2cProfiles (list nil nil nil nil) )        
		(setq doorFlags::p2cProfileHandles (list nil nil nil nil) )  
		(setq doorFlags::p2cFrameThick 55.0)                        
		;(setq doorFlags::p2cSpcRcp 1)
	))
	(mapcar '(lambda (x) (set (read (strcat _KSets_VariableModelName "_" x "KANATSETS")) (eval (read (strcat _KSets_VariableModelName "_AKANATSETS")))) ) _KSets_typeAList)
	;(mapcar '(lambda (x) (set (read (strcat _KSets_VariableModelName "_" x "_MAT_LAYER")) "ALUMINIUM_FRAME") ) _KSets_typeAList)
	;(mapcar '(lambda (x) (set (read (strcat _KSets_VariableModelName "_" x "_GLASS_MAT_LAYER")) "CAB_DOOR_GLASS") ) _KSets_typeAList)

	;d1bkanat d2bkanat d3bkanat ...
	;(mapcar '(lambda (d) (set (read (strcat _KSets_VariableModelName c "_AKANATSETS")) '((x z)(apply (read (strcat _KSets_VariableModelName "_AKANATSETS")) (list x z)))) ) _KSets_AlternativeBSufixList)
	;(mapcar '(lambda (d) (mapcar '(lambda (x) (set (read (strcat _KSets_VariableModelName d "_" x "KANATSETS")) (eval (read (strcat _KSets_VariableModelName "_AKANATSETS"))) ) ) _KSets_typeAList) ) _KSets_AlternativeBSufixList)
	;(mapcar '(lambda (d) (mapcar '(lambda (x) (set (read (strcat _KSets_VariableModelName d "_" x "_GLASS_MAT_LAYER")) "CAB_DOOR_GLASS") ) _KSets_typeAList)  ) _KSets_AlternativeBSufixList)
	;(mapcar '(lambda (d) (mapcar '(lambda (x) (set (read (strcat _KSets_VariableModelName d "_" x "_MAT_LAYER")) "ALUMINIUM_FRAME") ) _KSets_typeAList) ) _KSets_AlternativeBSufixList)

	(set (read (strcat _KSets_VariableModelName "_BKANATSETS")) '((x z) ;bkanat
		;(setq doorFlags::p2cDoorSource "INSOURCE")
		(setq doorFlags::p2cDoorSource "(list \"SANAL_##\" __AD_PANELTHICK)")
		(setq doorFlags::p2cEdges (list PvcKoduKAPAK PvcKoduKAPAK PvcKoduKAPAK PvcKoduKAPAK))          
		(setq doorFlags::p2cProfiles (list nil nil nil nil))        
		(setq doorFlags::p2cProfileHandles (list nil nil nil nil))  
		(setq doorFlags::p2cFrameThick 55.0)                        
		;(setq doorFlags::p2cSpcRcp 1)
	))
	(mapcar '(lambda (x) (set (read (strcat _KSets_VariableModelName "_" x "KANATSETS")) (eval (read (strcat _KSets_VariableModelName "_BKANATSETS")))) ) _KSets_typeBList)
	;(mapcar '(lambda (x) (set (read (strcat _KSets_VariableModelName "_" x "_MAT_LAYER")) "ALUMINIUM_FRAME") ) _KSets_typeBList)
	;(mapcar '(lambda (x) (set (read (strcat _KSets_VariableModelName "_" x "_GLASS_MAT_LAYER")) "CAB_DOOR_GLASS") ) _KSets_typeBList)

	;c1bkanat c2bkanat c3bkanat ...
	(mapcar '(lambda (c) (set (read (strcat _KSets_VariableModelName c "_BKANATSETS")) '((x z)(apply (read (strcat _KSets_VariableModelName "_BKANATSETS")) (list x z)))) ) _KSets_AlternativeBSufixList)
	(mapcar '(lambda (c) (mapcar '(lambda (x) (set (read (strcat _KSets_VariableModelName c "_" x "KANATSETS")) (eval (read (strcat _KSets_VariableModelName "_BKANATSETS"))) ) ) _KSets_typeBList) ) _KSets_AlternativeBSufixList)
	;(mapcar '(lambda (c) (mapcar '(lambda (x) (set (read (strcat _KSets_VariableModelName c "_" x "_GLASS_MAT_LAYER")) "CAB_DOOR_GLASS") ) _KSets_typeBList)  ) _KSets_AlternativeBSufixList)
	;(mapcar '(lambda (c) (mapcar '(lambda (x) (set (read (strcat _KSets_VariableModelName c "_" x "_MAT_LAYER")) "ALUMINIUM_FRAME") ) _KSets_typeBList) ) _KSets_AlternativeBSufixList)


	(set (read (strcat "postrun." _KSets_VariableModelName "_A")) '((x z) 	;;p2cLabour recete ornekleri, A ve B ayristirilmis . ulib labour icinden ayristirma iptal edilebilir.
		(post.itag (list (strcat _KSets_VariableModelName "KapakMontaj") (ifnull areaOfDoor.PARENT 0.0) "m2"))
		(post.kapPaKes (list nil (- pnlW.parent 3) (- pnlH.parent 3) 2.0 pnlMat.Parent pnlRot.Parent))
	))
	(set (read (strcat "postrun." _KSets_VariableModelName "_B")) '((x z)
		(post.itag (list (strcat _KSets_VariableModelName "KapakMontaj") (ifnull areaOfDoor.PARENT 0.0) "m2"))
		(post.kapPaKes (list nil (- pnlW.parent 3) (- pnlH.parent 3) 2.0 pnlMat.Parent pnlRot.Parent))
	))

;__________________________________________________________________________________________________________________________________________________________

;kanken kapaklar detaylandirilmadi

(defun KANKEN1_SETS()(setq doorFlags::p2cDoorSource "INSOURCE")(setq doorFlags::p2cEdges (list PvcKoduKAPAK PvcKoduKAPAK PvcKoduKAPAK PvcKoduKAPAK))(setq doorFlags::p2cFrameThick 55))
(defun KANKEN2_SETS()(setq doorFlags::p2cDoorSource "INSOURCE")(setq doorFlags::p2cEdges (list PvcKoduKAPAK PvcKoduKAPAK PvcKoduKAPAK PvcKoduKAPAK))(setq doorFlags::p2cFrameThick 55))
(defun KANKEN3_SETS()(setq doorFlags::p2cDoorSource "INSOURCE")(setq doorFlags::p2cEdges (list PvcKoduKAPAK PvcKoduKAPAK PvcKoduKAPAK PvcKoduKAPAK))(setq doorFlags::p2cFrameThick 55))
(defun KANKEN4_SETS()(setq doorFlags::p2cDoorSource "INSOURCE")(setq doorFlags::p2cEdges (list PvcKoduKAPAK PvcKoduKAPAK PvcKoduKAPAK PvcKoduKAPAK))(setq doorFlags::p2cFrameThick 55))
(defun KANKEN5_SETS()(setq doorFlags::p2cDoorSource "INSOURCE")(setq doorFlags::p2cEdges (list PvcKoduKAPAK PvcKoduKAPAK PvcKoduKAPAK PvcKoduKAPAK))(setq doorFlags::p2cFrameThick 55))
(defun KANKEN6_SETS()(setq doorFlags::p2cDoorSource "INSOURCE")(setq doorFlags::p2cEdges (list PvcKoduKAPAK PvcKoduKAPAK PvcKoduKAPAK PvcKoduKAPAK))(setq doorFlags::p2cFrameThick 55))

(defun KANKEN1C_SETS()(setq doorFlags::p2cDoorSource "INSOURCE")(setq doorFlags::p2cEdges (list PvcKoduKAPAK PvcKoduKAPAK PvcKoduKAPAK PvcKoduKAPAK))(setq doorFlags::p2cFrameThick 55))
(defun KANKEN2C_SETS()(setq doorFlags::p2cDoorSource "INSOURCE")(setq doorFlags::p2cEdges (list PvcKoduKAPAK PvcKoduKAPAK PvcKoduKAPAK PvcKoduKAPAK))(setq doorFlags::p2cFrameThick 55))
(defun KANKEN3C_SETS()(setq doorFlags::p2cDoorSource "INSOURCE")(setq doorFlags::p2cEdges (list PvcKoduKAPAK PvcKoduKAPAK PvcKoduKAPAK PvcKoduKAPAK))(setq doorFlags::p2cFrameThick 55))
(defun KANKEN4C_SETS()(setq doorFlags::p2cDoorSource "INSOURCE")(setq doorFlags::p2cEdges (list PvcKoduKAPAK PvcKoduKAPAK PvcKoduKAPAK PvcKoduKAPAK))(setq doorFlags::p2cFrameThick 55))
(defun KANKEN5C_SETS()(setq doorFlags::p2cDoorSource "INSOURCE")(setq doorFlags::p2cEdges (list PvcKoduKAPAK PvcKoduKAPAK PvcKoduKAPAK PvcKoduKAPAK))(setq doorFlags::p2cFrameThick 55))
(defun KANKEN6C_SETS()(setq doorFlags::p2cDoorSource "INSOURCE")(setq doorFlags::p2cEdges (list PvcKoduKAPAK PvcKoduKAPAK PvcKoduKAPAK PvcKoduKAPAK))(setq doorFlags::p2cFrameThick 55))

;__________________________________________________________________________________________________________________________________________________________

(defun RESIM_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "RESIM" "_" x "KANATSETS")) RESIM_AKANATSETS) ) _KSets_typeAList)

(defun RESIM_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "RESIM" "_" x "KANATSETS")) RESIM_BKANATSETS) ) _KSets_typeBList)

;__________________________________________________________________________________________________________________________________________________________

(defun 2RENKBANT_AKANATSETS(x z)
	(setq doorFlags::p2cDoorSource "INSOURCE")
	(setq doorFlags::p2cEdges (list "2RENKBANT" "2RENKBANT" "2RENKBANT" "2RENKBANT"))
	(setq doorFlags::p2cFrameThick 55)
)
(mapcar '(lambda (x) (set (read (strcat "2RENKBANT" "_" x "KANATSETS")) 2RENKBANT_AKANATSETS) ) _KSets_typeAList)

(defun 2RENKBANT_BKANATSETS(x z)
	(setq doorFlags::p2cDoorSource "INSOURCE")
	(setq doorFlags::p2cEdges (list "2RENKBANT" "2RENKBANT" "2RENKBANT" "2RENKBANT"))
	(setq doorFlags::p2cFrameThick 55)
)
(mapcar '(lambda (x) (set (read (strcat "2RENKBANT" "_" x "KANATSETS")) 2RENKBANT_BKANATSETS) ) _KSets_typeBList)

;__________________________________________________________________________________________________________________________________________________________

(defun PVC08_AKANATSETS(x z)
	(setq doorFlags::p2cDoorSource "INSOURCE")
	(setq doorFlags::p2cEdges (list "PVC08mm" "PVC08mm" "PVC08mm" "PVC08mm"))
	(setq doorFlags::p2cFrameThick 55)
)
(mapcar '(lambda (x) (set (read (strcat "PVC08" "_" x "KANATSETS")) PVC08_AKANATSETS) ) _KSets_typeAList)

(defun PVC08_BKANATSETS(x z)
	(setq doorFlags::p2cDoorSource "INSOURCE")
	(setq doorFlags::p2cFrameThick 55)
	(cond 
		((member kulp '("0-")) (setq doorFlags::p2cProfiles (list prfKS prfKS prfKS prfKS)))
		((member kulp '("K-" "KD")) (setq doorFlags::p2cProfiles (list prfKL prfKS prfKS prfKS)))
		((member kulp '("G-" "GD")) (setq doorFlags::p2cProfiles (list prfKS prfKS prfKL prfKS)))
		((member kulp '("D-")) (setq doorFlags::p2cProfiles (list prfKS prfKL prfKS prfKS)))
	)
)
(mapcar '(lambda (x) (set (read (strcat "PVC08" "_" x "KANATSETS")) PVC08_BKANATSETS) ) _KSets_typeBList)
(mapcar '(lambda (x) (set (read (strcat "PVC08" "_" x "_MAT_LAYER")) "ALUMINIUM_FRAME") ) _KSets_typeBList)

;__________________________________________________________________________________________________________________________________________________________

(defun PVC040_AKANATSETS(x z)
	(setq doorFlags::p2cDoorSource "INSOURCE")
	(setq doorFlags::p2cEdges (list "PVC04mm" "PVC04mm" "PVC04mm" "PVC04mm"))
	(setq doorFlags::p2cFrameThick 55)
)
(mapcar '(lambda (x) (set (read (strcat "PVC040" "_" x "KANATSETS")) PVC040_AKANATSETS) ) _KSets_typeAList)

(defun PVC040_BKANATSETS(x z)
	(setq doorFlags::p2cDoorSource "INSOURCE")
	(setq doorFlags::p2cFrameThick 55)
	(cond 
		((member kulp '("0-")) (setq doorFlags::p2cProfiles (list prfKS prfKS prfKS prfKS)))
		((member kulp '("D-")) (setq doorFlags::p2cProfiles (list prfKS prfKL prfKS prfKS)))
		(T (setq doorFlags::p2cProfiles (list prfKS prfKS prfKL prfKS)))
	)
)
(mapcar '(lambda (x) (set (read (strcat "PVC040" "_" x "KANATSETS")) PVC040_BKANATSETS) ) _KSets_typeBList)
(mapcar '(lambda (x) (set (read (strcat "PVC040" "_" x "_MAT_LAYER")) "ALUMINIUM_FRAME") ) _KSets_typeBList)

;__________________________________________________________________________________________________________________________________________________________

(defun PVC1_AKANATSETS(x z)
	(setq doorFlags::p2cDoorSource "INSOURCE")
	(setq doorFlags::p2cEdges (list "PVC1mm" "PVC1mm" "PVC1mm" "PVC1mm"))
	(setq doorFlags::p2cFrameThick 55)
)
(mapcar '(lambda (x) (set (read (strcat "PVC1" "_" x "KANATSETS")) PVC1_AKANATSETS) ) _KSets_typeAList)

(defun PVC1_BKANATSETS(x z)
	(setq doorFlags::p2cDoorSource "INSOURCE")
	(setq doorFlags::p2cFrameThick 55)
	(cond 
		((member kulp '("0-")) (setq doorFlags::p2cProfiles (list prfKS prfKS prfKS prfKS)))
		((member kulp '("D-")) (setq doorFlags::p2cProfiles (list prfKS prfKL prfKS prfKS)))
		(T (setq doorFlags::p2cProfiles (list prfKS prfKS prfKL prfKS)))
	)
)
(mapcar '(lambda (x) (set (read (strcat "PVC1" "_" x "KANATSETS")) PVC1_BKANATSETS) ) _KSets_typeBList)
(mapcar '(lambda (x) (set (read (strcat "PVC1" "_" x "_MAT_LAYER")) "ALUMINIUM_FRAME") ) _KSets_typeBList)
;__________________________________________________________________________________________________________________________________________________________

(defun PVC2_AKANATSETS(x z)
	(setq doorFlags::p2cDoorSource "INSOURCE")
	(setq doorFlags::p2cEdges (list "PVC2mm" "PVC2mm" "PVC2mm" "PVC2mm"))
	(setq doorFlags::p2cFrameThick 55)
)
(mapcar '(lambda (x) (set (read (strcat "PVC2" "_" x "KANATSETS")) PVC2_AKANATSETS) ) _KSets_typeAList)

(defun PVC2_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKS prfKS prfKL prfKS)))
	)
)
(mapcar '(lambda (x) (set (read (strcat "PVC2" "_" x "KANATSETS")) PVC2_BKANATSETS) ) _KSets_typeBList)
(mapcar '(lambda (x) (set (read (strcat "PVC2" "_" x "_MAT_LAYER")) "ALUMINIUM_FRAME") ) _KSets_typeBList)

;__________________________________________________________________________________________________________________________________________________________

(defun ALU2_AKANATSETS(x z)
	(setq doorFlags::p2cDoorSource "INSOURCE")
	(setq doorFlags::p2cEdges (list nil nil nil nil))
	(setq doorFlags::p2cProfiles (list prfT prfT prfT prfT))
	(setq doorFlags::p2cFrameThick 55)
)
(mapcar '(lambda (x) (set (read (strcat "ALU2" "_" x "KANATSETS")) ALU2_AKANATSETS) ) _KSets_typeAList)

(defun ALU2_BKANATSETS(x z)
	(setq doorFlags::p2cDoorSource "INSOURCE")
	(setq doorFlags::p2cEdges (list nil nil nil nil))
	(setq doorFlags::p2cProfiles (list prfT prfT prfT prfT))
	(setq doorFlags::p2cFrameThick 55)
)
(mapcar '(lambda (x) (set (read (strcat "ALU2" "_" x "KANATSETS")) ALU2_BKANATSETS) ) _KSets_typeBList)

;__________________________________________________________________________________________________________________________________________________________

(defun DUZKBANT_AKANATSETS(x z)
	(setq doorFlags::p2cDoorSource "INSOURCE")
	(setq doorFlags::p2cEdges (list "PVC2mm" "PVC2mm" "PVC2mm" "PVC2mm"))
	(setq doorFlags::p2cFrameThick 55)
)
(mapcar '(lambda (x) (set (read (strcat "DUZKBANT" "_" x "KANATSETS")) DUZKBANT_AKANATSETS) ) _KSets_typeAList)

(defun DUZKBANT_BKANATSETS(x z)
	(setq doorFlags::p2cDoorSource "INSOURCE")
	(setq doorFlags::p2cEdges (list "PVC2mm" "PVC2mm" "PVC2mm" "PVC2mm"))
	(setq doorFlags::p2cFrameThick 55)
)
(mapcar '(lambda (x) (set (read (strcat "DUZKBANT" "_" x "KANATSETS")) DUZKBANT_BKANATSETS) ) _KSets_typeBList)

;__________________________________________________________________________________________________________________________________________________________

(defun SOFT3_AKANATSETS(x z)
	(setq doorFlags::p2cDoorSource "INSOURCE")
	(setq doorFlags::p2cEdges (list nil nil nil nil))
	(setq doorFlags::p2cFrameThick 55)
)
(mapcar '(lambda (x) (set (read (strcat "SOFT3" "_" x "KANATSETS")) SOFT3_AKANATSETS) ) _KSets_typeAList)

(defun SOFT3_BKANATSETS(x z)
	(setq doorFlags::p2cDoorSource "INSOURCE")
	(setq doorFlags::p2cEdges (list nil nil nil nil))
	(setq doorFlags::p2cFrameThick 55)
)
(mapcar '(lambda (x) (set (read (strcat "SOFT3" "_" x "KANATSETS")) SOFT3_BKANATSETS) ) _KSets_typeBList)

;__________________________________________________________________________________________________________________________________________________________

(defun SOFT4_AKANATSETS(x z)
	(setq doorFlags::p2cDoorSource "INSOURCE")
	(setq doorFlags::p2cEdges (list nil nil nil nil))
	(setq doorFlags::p2cFrameThick 55)
)
(mapcar '(lambda (x) (set (read (strcat "SOFT4" "_" x "KANATSETS")) SOFT4_AKANATSETS) ) _KSets_typeAList)

(defun SOFT4_BKANATSETS(x z)
	(setq doorFlags::p2cDoorSource "INSOURCE")
	(setq doorFlags::p2cEdges (list nil nil nil nil))
	(setq doorFlags::p2cFrameThick 55)
)
(mapcar '(lambda (x) (set (read (strcat "SOFT4" "_" x "KANATSETS")) SOFT4_BKANATSETS) ) _KSets_typeBList)

;__________________________________________________________________________________________________________________________________________________________

(defun SOFT5_AKANATSETS(x z)
	(setq doorFlags::p2cDoorSource "INSOURCE")
	(setq doorFlags::p2cEdges (list nil nil nil nil))
	(setq doorFlags::p2cFrameThick 55)
)
(mapcar '(lambda (x) (set (read (strcat "SOFT5" "_" x "KANATSETS")) SOFT5_AKANATSETS) ) _KSets_typeAList)

(defun SOFT5_BKANATSETS(x z)
	(setq doorFlags::p2cDoorSource "INSOURCE")
	(setq doorFlags::p2cEdges (list nil nil nil nil))
	(setq doorFlags::p2cFrameThick 55)
)
(mapcar '(lambda (x) (set (read (strcat "SOFT5" "_" x "KANATSETS")) SOFT5_BKANATSETS) ) _KSets_typeBList)

;__________________________________________________________________________________________________________________________________________________________

(defun 2PAH_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "2PAH" "_" x "KANATSETS")) 2PAH_AKANATSETS) ) _KSets_typeAList)

(defun 2PAH_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "2PAH" "_" x "KANATSETS")) 2PAH_BKANATSETS) ) _KSets_typeBList)

;__________________________________________________________________________________________________________________________________________________________

(defun PAH2_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "PAH2" "_" x "KANATSETS")) PAH2_AKANATSETS) ) _KSets_typeAList)

(defun PAH2_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "PAH2" "_" x "KANATSETS")) PAH2_BKANATSETS) ) _KSets_typeBList)

;__________________________________________________________________________________________________________________________________________________________

(defun PAH3_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "PAH3" "_" x "KANATSETS")) PAH3_AKANATSETS) ) _KSets_typeAList)

(defun PAH3_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "PAH3" "_" x "KANATSETS")) PAH3_BKANATSETS) ) _KSets_typeBList)

;__________________________________________________________________________________________________________________________________________________________

(defun PAH4_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "PAH4" "_" x "KANATSETS")) PAH4_AKANATSETS) ) _KSets_typeAList)

(defun PAH4_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "PAH4" "_" x "KANATSETS")) PAH4_BKANATSETS) ) _KSets_typeBList)

;__________________________________________________________________________________________________________________________________________________________

(defun ALU_AKANATSETS(x z)
	(setq doorFlags::p2cDoorSource "INSOURCE")
	(setq doorFlags::p2cEdges (list nil nil nil nil))
	(setq doorFlags::p2cProfiles (list prfT prfT prfT prfT))
	(setq doorFlags::p2cFrameThick 55)
)
(mapcar '(lambda (x) (set (read (strcat "ALU" "_" x "KANATSETS")) ALU_AKANATSETS) ) _KSets_typeAList)

(defun ALU_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("K-" "G-" )) (setq doorFlags::p2cProfiles (list prfKL prfKS prfKS prfKS)))
		((member kulp '("GD" "KD" "D-")) (setq doorFlags::p2cProfiles (list prfKS prfKL prfKS prfKS)))
	)
)
(mapcar '(lambda (x) (set (read (strcat "ALU" "_" x "KANATSETS")) ALU_BKANATSETS) ) _KSets_typeBList)
(mapcar '(lambda (x) (set (read (strcat "ALU" "_" x "_MAT_LAYER")) "ALUMINIUM_FRAME") ) _KSets_typeBList)

;__________________________________________________________________________________________________________________________________________________________

(defun PAHLIM_AKANATSETS(x z)
	(setq doorFlags::p2cDoorSource "INSOURCE")
	(setq doorFlags::p2cEdges (list nil nil nil nil))
	(setq doorFlags::p2cProfiles (list nil nil nil nil))
	(setq doorFlags::p2cFrameThick 55)
)
(mapcar '(lambda (x) (set (read (strcat "PAHLIM" "_" x "KANATSETS")) PAHLIM_AKANATSETS) ) _KSets_typeAList)

(defun PAHLIM_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("K-" "G-" )) (setq doorFlags::p2cProfiles (list prfKL prfKS prfKS prfKS)))
		(T (setq doorFlags::p2cProfiles (list prfKS prfKL prfKS prfKS)))
	)
)
(mapcar '(lambda (x) (set (read (strcat "PAHLIM" "_" x "KANATSETS")) PAHLIM_BKANATSETS) ) _KSets_typeBList)
(mapcar '(lambda (x) (set (read (strcat "PAHLIM" "_" x "_MAT_LAYER")) "ALUMINIUM_FRAME") ) _KSets_typeBList)

;__________________________________________________________________________________________________________________________________________________________

(defun ALMC_AKANATSETS(x z)
	(setq doorFlags::p2cDoorSource "INSOURCE")
	(setq doorFlags::p2cEdges (list nil nil nil nil))
	(setq doorFlags::p2cProfiles (list prfT2 prfT2 prfT2 prfT2))
	(setq doorFlags::p2cFrameThick 55)
)
(mapcar '(lambda (x) (set (read (strcat "ALMC" "_" x "KANATSETS")) ALMC_AKANATSETS) ) _KSets_typeAList)

(defun ALMC_BKANATSETS(x z)
	(setq doorFlags::p2cDoorSource "INSOURCE")
	(setq doorFlags::p2cFrameThick 55)
	(cond 
		((member kulp '("0-")) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "ALMC" "_" x "KANATSETS")) ALMC_BKANATSETS) ) _KSets_typeBList)
(mapcar '(lambda (x) (set (read (strcat "ALMC" "_" x "_MAT_LAYER")) "ALUMINIUM_FRAME") ) _KSets_typeBList)

;__________________________________________________________________________________________________________________________________________________________

 (defun LKAPAK_AKANATSETS(x z)
	(setq doorFlags::p2cDoorSource "INSOURCE")
	(setq doorFlags::p2cEdges (list nil nil nil nil))
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(cond 
		((member kulp '("0-" )) (setq doorFlags::p2cProfiles (list nil nil nil nil)))
		((member kulp '("D-")) 	(setq doorFlags::p2cProfiles (list nil prfA nil nil)))
		(T 	 (setq doorFlags::p2cProfiles (list prfA nil nil nil)))
	)
)
(mapcar '(lambda (x) (set (read (strcat "LKAPAK" "_" x "KANATSETS")) LKAPAK_AKANATSETS) ) _KSets_typeAList)
(mapcar '(lambda (x) (set (read (strcat "LKAPAK" "_" x "_MAT_LAYER")) "HANDLES_AND_KNOBS") ) _KSets_typeAList)

(defun LKAPAK_BKANATSETS(x z)
	(setq doorFlags::p2cDoorSource "INSOURCE")
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(cond 
		((member kulp '("0-" )) (setq doorFlags::p2cProfiles (list nil nil nil nil)))
		((member kulp '("D-")) 	(setq doorFlags::p2cProfiles (list nil prfA nil nil)))
		(T 	 (setq doorFlags::p2cProfiles (list prfA nil nil nil)))
	)
)
(mapcar '(lambda (x) (set (read (strcat "LKAPAK" "_" x "KANATSETS")) LKAPAK_BKANATSETS) ) _KSets_typeBList)
(mapcar '(lambda (x) (set (read (strcat "LKAPAK" "_" x "_MAT_LAYER")) "ALUMINIUM_FRAME") ) _KSets_typeBList)

;__________________________________________________________________________________________________________________________________________________________

(defun JKAPAK_AKANATSETS(x z)
	(setq doorFlags::p2cDoorSource "INSOURCE")
	(setq doorFlags::p2cEdges (list nil nil nil nil))
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(cond 
		((member kulp '("0-" )) (setq doorFlags::p2cProfiles (list nil nil nil nil)))
		((member kulp '("D-")) 	(setq doorFlags::p2cProfiles (list nil prfA nil nil)))
		(T 	 (setq doorFlags::p2cProfiles (list prfA nil nil nil)))
	)
)
(mapcar '(lambda (x) (set (read (strcat "JKAPAK" "_" x "KANATSETS")) JKAPAK_AKANATSETS) ) _KSets_typeAList)
(mapcar '(lambda (x) (set (read (strcat "JKAPAK" "_" x "_MAT_LAYER")) "ALUMINIUM_FRAME") ) _KSets_typeAList)

(defun JKAPAK_BKANATSETS(x z)
	(setq doorFlags::p2cDoorSource "INSOURCE")
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(cond 
		((member kulp '("0-" )) (setq doorFlags::p2cProfiles (list nil nil nil nil)))
		((member kulp '("D-")) 	(setq doorFlags::p2cProfiles (list nil prfA nil nil)))
		(T 	 (setq doorFlags::p2cProfiles (list prfA nil nil nil)))
	)
)
(mapcar '(lambda (x) (set (read (strcat "JKAPAK" "_" x "KANATSETS")) JKAPAK_BKANATSETS) ) _KSets_typeBList)
(mapcar '(lambda (x) (set (read (strcat "JKAPAK" "_" x "_MAT_LAYER")) "ALUMINIUM_FRAME") ) _KSets_typeBList)

;__________________________________________________________________________________________________________________________________________________________

(defun OYUKKAPAK_AKANATSETS(x z)
	(setq doorFlags::p2cDoorSource "INSOURCE")
	(setq doorFlags::p2cEdges (list nil nil nil nil))
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(setq doorFlags::p2cProfiles (list nil nil nil nil))
)
(mapcar '(lambda (x) (set (read (strcat "OYUKKAPAK" "_" x "KANATSETS")) OYUKKAPAK_AKANATSETS) ) _KSets_typeAList)

(defun OYUKKAPAK_BKANATSETS(x z)
	(setq doorFlags::p2cDoorSource "INSOURCE")
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(setq doorFlags::p2cProfiles (list nil nil nil nil))
)
(mapcar '(lambda (x) (set (read (strcat "OYUKKAPAK" "_" x "KANATSETS")) OYUKKAPAK_BKANATSETS) ) _KSets_typeBList)

;__________________________________________________________________________________________________________________________________________________________

(defun JOYUKRENKLI_AKANATSETS(x z)
	(setq doorFlags::p2cDoorSource "INSOURCE")
	(setq doorFlags::p2cEdges (list nil nil nil nil))
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(setq doorFlags::p2cProfiles (list nil nil nil nil))
)
(mapcar '(lambda (x) (set (read (strcat "JOYUKRENKLI" "_" x "KANATSETS")) JOYUKRENKLI_AKANATSETS) ) _KSets_typeAList)

(defun OYUKKAPAK_BKANATSETS(x z)
	(setq doorFlags::p2cDoorSource "INSOURCE")
	(setq doorFlags::p2cFrameThick 55)
	(cond 
		((member kulp '("0-" )) (setq doorFlags::p2cEdges (list PvcKoduKAPAK PvcKoduKAPAK PvcKoduKAPAK PvcKoduKAPAK)))
		((member kulp '("D-")) 	 (setq doorFlags::p2cEdges (list PvcKoduKAPAK PvcKoduProfil PvcKoduKAPAK PvcKoduKAPAK)))
		(T 	 (setq doorFlags::p2cEdges (list PvcKoduProfil PvcKoduKAPAK PvcKoduKAPAK PvcKoduKAPAK)))
	)
	(setq doorFlags::p2cProfiles (list nil nil nil nil))
)
(mapcar '(lambda (x) (set (read (strcat "JOYUKRENKLI" "_" x "KANATSETS")) JOYUKRENKLI_BKANATSETS) ) _KSets_typeBList)

;__________________________________________________________________________________________________________________________________________________________

(defun ALUBOYPRFL_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "ALUBOYPRFL" "_" x "KANATSETS")) ALUBOYPRFL_AKANATSETS) ) _KSets_typeAList)

(defun ALUBOYPRFL_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("K-" "G-" )) (setq doorFlags::p2cProfiles (list prfKL prfKS prfKS prfKS)))
		(T (setq doorFlags::p2cProfiles (list prfKS prfKL prfKS prfKS)))
	)
)
(mapcar '(lambda (x) (set (read (strcat "ALUBOYPRFL" "_" x "KANATSETS")) ALUBOYPRFL_BKANATSETS) ) _KSets_typeBList)
(mapcar '(lambda (x) (set (read (strcat "ALUBOYPRFL" "_" x "_MAT_LAYER")) "ALUMINIUM_FRAME") ) _KSets_typeBList)

;__________________________________________________________________________________________________________________________________________________________

(defun ALMKLP2C_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "ALMKLP2C" "_" x "KANATSETS")) ALMKLP2C_AKANATSETS) ) _KSets_typeAList)

(defun ALMKLP2C_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("K-" "G-" )) (setq doorFlags::p2cProfiles (list prfKL2 prfKS prfKS prfKS)))
		(T (setq doorFlags::p2cProfiles (list prfKS prfKL2 prfKS prfKS)))
	)
)
(mapcar '(lambda (x) (set (read (strcat "ALMKLP2C" "_" x "KANATSETS")) ALMKLP2C_BKANATSETS) ) _KSets_typeBList)
(mapcar '(lambda (x) (set (read (strcat "ALMKLP2C" "_" x "_MAT_LAYER")) "ALUMINIUM_FRAME") ) _KSets_typeBList)

;__________________________________________________________________________________________________________________________________________________________

(defun JKULPYN_AKANATSETS(x z)
	(setq doorFlags::p2cDoorSource "INSOURCE")
	(setq doorFlags::p2cEdges (list PvcKoduKAPAK nil PvcKoduKAPAK PvcKoduKAPAK))
	(setq doorFlags::p2cFrameThick 55)
)
(mapcar '(lambda (x) (set (read (strcat "JKULPYN" "_" x "KANATSETS")) JKULPYN_AKANATSETS) ) _KSets_typeAList)

(defun JKULPYN_BKANATSETS(x z)
	(setq doorFlags::p2cDoorSource "INSOURCE")
	(setq doorFlags::p2cEdges (list PvcKoduKAPAK nil PvcKoduKAPAK PvcKoduKAPAK))
	(setq doorFlags::p2cFrameThick 55)
)
(mapcar '(lambda (x) (set (read (strcat "JKULPYN" "_" x "KANATSETS")) JKULPYN_BKANATSETS) ) _KSets_typeBList)

;__________________________________________________________________________________________________________________________________________________________

(defun JKULP_AKANATSETS(x z)
	(setq doorFlags::p2cDoorSource "INSOURCE")
	(setq doorFlags::p2cEdges (list nil PvcKoduKAPAK PvcKoduKAPAK PvcKoduKAPAK))
	(setq doorFlags::p2cFrameThick 55)
)
(mapcar '(lambda (x) (set (read (strcat "JKULP" "_" x "KANATSETS")) JKULP_AKANATSETS) ) _KSets_typeAList)

(defun JKULP_BKANATSETS(x z)
	(setq doorFlags::p2cDoorSource "INSOURCE")
	(setq doorFlags::p2cEdges (list nil PvcKoduKAPAK PvcKoduKAPAK PvcKoduKAPAK))
	(setq doorFlags::p2cFrameThick 55)
)
(mapcar '(lambda (x) (set (read (strcat "JKULP" "_" x "KANATSETS")) JKULP_BKANATSETS) ) _KSets_typeBList)

;__________________________________________________________________________________________________________________________________________________________

(defun P0003_AKANATSETS(x z)
	(setq doorFlags::p2cDoorSource "INSOURCE")
	(setq doorFlags::p2cEdges (list nil PvcKoduKAPAK PvcKoduKAPAK PvcKoduKAPAK))
	(setq doorFlags::p2cFrameThick 55)
)
(mapcar '(lambda (x) (set (read (strcat "P0003" "_" x "KANATSETS")) P0003_AKANATSETS) ) _KSets_typeAList)

(defun P0003_BKANATSETS(x z)
	(setq doorFlags::p2cDoorSource "INSOURCE")
	(setq doorFlags::p2cEdges (list nil PvcKoduKAPAK PvcKoduKAPAK PvcKoduKAPAK))
	(setq doorFlags::p2cFrameThick 55)
)
(mapcar '(lambda (x) (set (read (strcat "P0003" "_" x "KANATSETS")) P0003_BKANATSETS) ) _KSets_typeBList)

;__________________________________________________________________________________________________________________________________________________________

(defun P00D3_AKANATSETS(x z)
	(setq doorFlags::p2cDoorSource "INSOURCE")
	(setq doorFlags::p2cEdges (list PvcKoduKAPAK nil PvcKoduKAPAK PvcKoduKAPAK))
	(setq doorFlags::p2cFrameThick 55)
)
(mapcar '(lambda (x) (set (read (strcat "P00D3" "_" x "KANATSETS")) P00D3_AKANATSETS) ) _KSets_typeAList)

(defun P00D3_BKANATSETS(x z)
	(setq doorFlags::p2cDoorSource "INSOURCE")
	(setq doorFlags::p2cEdges (list PvcKoduKAPAK nil PvcKoduKAPAK PvcKoduKAPAK))
	(setq doorFlags::p2cFrameThick 55)
)
(mapcar '(lambda (x) (set (read (strcat "P00D3" "_" x "KANATSETS")) P00D3_BKANATSETS) ) _KSets_typeBList)

;__________________________________________________________________________________________________________________________________________________________

(defun PL05_AKANATSETS(x z)
	(setq doorFlags::p2cDoorSource "INSOURCE")
	(cond 
		(	(member kulp '("0-"))
			(setq doorFlags::p2cEdges (list PvcKoduKAPAK PvcKoduKAPAK PvcKoduKAPAK PvcKoduKAPAK))
			(setq doorFlags::p2cProfileHandles (list nil nil nil nil))
			(setq doorFlags::p2cProfiles (list nil nil nil nil))
		)
		(	T 
			(setq doorFlags::p2cEdges (list nil PvcKoduKAPAK PvcKoduKAPAK PvcKoduKAPAK))
			(setq doorFlags::p2cProfileHandles (list entT2 nil nil nil))
			(setq doorFlags::p2cProfiles (list entT2 nil nil nil))
		)
	)
	(setq doorFlags::p2cFrameThick 55)
)
(mapcar '(lambda (x) (set (read (strcat "PL05" "_" x "KANATSETS")) PL05_AKANATSETS) ) _KSets_typeAList)
;(mapcar '(lambda (x) (set (read (strcat "PL05" "_" x "_MAT_LAYER")) "ALUMINIUM_FRAME") ) _KSets_typeAList)

(defun PL05_BKANATSETS(x z)
	(setq doorFlags::p2cDoorSource "INSOURCE")
	(cond 
		(	(member kulp '("0-"))
			(setq doorFlags::p2cEdges (list PvcKoduKAPAK PvcKoduKAPAK PvcKoduKAPAK PvcKoduKAPAK))
			(setq doorFlags::p2cProfileHandles (list nil nil nil nil))
			(setq doorFlags::p2cProfiles (list nil nil nil nil))
		)
		(	T 
			(setq doorFlags::p2cEdges (list nil PvcKoduKAPAK PvcKoduKAPAK PvcKoduKAPAK))
			(setq doorFlags::p2cProfileHandles (list entT2 nil nil nil))
			(setq doorFlags::p2cProfiles (list entT2 nil nil nil))
		)
	)
	(setq doorFlags::p2cFrameThick 55)
)
(mapcar '(lambda (x) (set (read (strcat "PL05" "_" x "KANATSETS")) PL05_BKANATSETS) ) _KSets_typeBList)
;(mapcar '(lambda (x) (set (read (strcat "PL05" "_" x "_MAT_LAYER")) "ALUMINIUM_FRAME") ) _KSets_typeBList)

;__________________________________________________________________________________________________________________________________________________________

(defun PLD5_AKANATSETS(x z)
	(setq doorFlags::p2cDoorSource "INSOURCE")
	(cond 
		(	(member kulp '("0-"))
			(setq doorFlags::p2cEdges (list PvcKoduKAPAK PvcKoduKAPAK PvcKoduKAPAK PvcKoduKAPAK))
			(setq doorFlags::p2cProfileHandles (list nil nil nil nil))
			(setq doorFlags::p2cProfiles (list nil nil nil nil))
		)
		(	T 
			(setq doorFlags::p2cEdges (list PvcKoduKAPAK nil PvcKoduKAPAK PvcKoduKAPAK))
			(setq doorFlags::p2cProfileHandles (list nil entT2 nil nil))
			(setq doorFlags::p2cProfiles (list nil entT2 nil nil))
		)
	)
	(setq doorFlags::p2cFrameThick 55)
)
(mapcar '(lambda (x) (set (read (strcat "PLD5" "_" x "KANATSETS")) PLD5_AKANATSETS) ) _KSets_typeAList)
;(mapcar '(lambda (x) (set (read (strcat "PLD5" "_" x "_MAT_LAYER")) "ALUMINIUM_FRAME") ) _KSets_typeAList)

(defun PLD5_BKANATSETS(x z)
	(setq doorFlags::p2cDoorSource "INSOURCE")
	(cond 
		(	(member kulp '("0-"))
			(setq doorFlags::p2cEdges (list PvcKoduKAPAK PvcKoduKAPAK PvcKoduKAPAK PvcKoduKAPAK))
			(setq doorFlags::p2cProfileHandles (list nil nil nil nil))
			(setq doorFlags::p2cProfiles (list nil nil nil nil))
		)
		(	T 
			(setq doorFlags::p2cEdges (list PvcKoduKAPAK nil PvcKoduKAPAK PvcKoduKAPAK))
			(setq doorFlags::p2cProfileHandles (list nil entT2 nil nil))
			(setq doorFlags::p2cProfiles (list nil entT2 nil nil))
		)
	)
	(setq doorFlags::p2cFrameThick 55)
)
(mapcar '(lambda (x) (set (read (strcat "PLD5" "_" x "KANATSETS")) PLD5_BKANATSETS) ) _KSets_typeBList)
;(mapcar '(lambda (x) (set (read (strcat "PLD5" "_" x "_MAT_LAYER")) "ALUMINIUM_FRAME") ) _KSets_typeBList)

;__________________________________________________________________________________________________________________________________________________________

(defun TEMP300_AKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		((member kulp '("K-" "KD")) (setq doorFlags::p2cEdges (list nil PvcKoduKAPAK PvcKoduKAPAK PvcKoduKAPAK)))
		(T (setq doorFlags::p2cEdges (list PvcKoduKAPAK PvcKoduKAPAK nil PvcKoduKAPAK)))
	)
	(cond 
		((member kulp '("0-" )) (setq doorFlags::p2cProfileHandles (list nil nil nil nil)))
		((member kulp '("K-" "KD")) (setq doorFlags::p2cProfileHandles (list entT3 nil nil nil)))
		(T (setq doorFlags::p2cProfileHandles (list nil nil entT3 nil)))
	)
)
(mapcar '(lambda (x) (set (read (strcat "TEMP300" "_" x "KANATSETS")) TEMP300_AKANATSETS) ) _KSets_typeAList)

(defun TEMP300_BKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		(T (setq doorFlags::p2cEdges (list nil PvcKoduKAPAK PvcKoduKAPAK PvcKoduKAPAK)))
	)
	(cond 
		((member kulp '("0-" )) (setq doorFlags::p2cProfileHandles (list nil nil nil nil)))
		(T (setq doorFlags::p2cProfileHandles (list entT3 nil nil nil)))
	)
)
(mapcar '(lambda (x) (set (read (strcat "TEMP300" "_" x "KANATSETS")) TEMP300_BKANATSETS) ) _KSets_typeBList)

;__________________________________________________________________________________________________________________________________________________________

(defun TEMP400_AKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		(T (setq doorFlags::p2cEdges (list nil PvcKoduKAPAK PvcKoduKAPAK PvcKoduKAPAK)))
	)
	(cond 
		((member kulp '("0-" )) (setq doorFlags::p2cProfileHandles (list nil nil nil nil)))
		(T (setq doorFlags::p2cProfileHandles (list entT4 nil nil nil)))
	)
)
(mapcar '(lambda (x) (set (read (strcat "TEMP400" "_" x "KANATSETS")) TEMP400_AKANATSETS) ) _KSets_typeAList)

(defun TEMP400_BKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		(T (setq doorFlags::p2cEdges (list nil PvcKoduKAPAK PvcKoduKAPAK PvcKoduKAPAK)))
	)
	(cond 
		((member kulp '("0-" )) (setq doorFlags::p2cProfileHandles (list nil nil nil nil)))
		(T (setq doorFlags::p2cProfileHandles (list entT4 nil nil nil)))
	)
)
(mapcar '(lambda (x) (set (read (strcat "TEMP400" "_" x "KANATSETS")) TEMP400_BKANATSETS) ) _KSets_typeBList)

;__________________________________________________________________________________________________________________________________________________________

(defun KKULP_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "KKULP" "_" x "KANATSETS")) KKULP_AKANATSETS) ) _KSets_typeAList)

(defun KKULP_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "KKULP" "_" x "KANATSETS")) KKULP_BKANATSETS) ) _KSets_typeBList)
(mapcar '(lambda (x) (set (read (strcat "KKULP" "_" x "_MAT_LAYER")) "ALUMINIUM_FRAME") ) _KSets_typeBList)

;__________________________________________________________________________________________________________________________________________________________

(defun MCIT_AKANATSETS(x z)
	(setq doorFlags::p2cDoorSource "INSOURCE")
	(setq doorFlags::p2cEdges (list nil PvcKoduKAPAK PvcKoduKAPAK PvcKoduKAPAK))
	(setq doorFlags::p2cProfileHandles (list entT4 nil nil nil))
	(setq doorFlags::p2cFrameThick 55)
)
(mapcar '(lambda (x) (set (read (strcat "MCIT" "_" x "KANATSETS")) MCIT_AKANATSETS) ) _KSets_typeAList)

(defun MCIT_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "MCIT" "_" x "KANATSETS")) MCIT_BKANATSETS) ) _KSets_typeBList)
(mapcar '(lambda (x) (set (read (strcat "MCIT" "_" x "_MAT_LAYER")) "ALUMINIUM_FRAME") ) _KSets_typeBList)

;__________________________________________________________________________________________________________________________________________________________

(defun AKULP_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "AKULP" "_" x "KANATSETS")) AKULP_AKANATSETS) ) _KSets_typeAList)

(defun AKULP_BKANATSETS(x z)
	(setq doorFlags::p2cDoorSource "INSOURCE")
	(setq doorFlags::p2cFrameThick 55)
	(setq doorFlags::p2cProfiles (list nil nil nil nil))
)
(mapcar '(lambda (x) (set (read (strcat "AKULP" "_" x "KANATSETS")) AKULP_BKANATSETS) ) _KSets_typeBList)
(mapcar '(lambda (x) (set (read (strcat "AKULP" "_" x "_MAT_LAYER")) "ALUMINIUM_FRAME") ) _KSets_typeBList)

;__________________________________________________________________________________________________________________________________________________________

(defun KKULPC_AKANATSETS(x z)
	(setq doorFlags::p2cDoorSource "INSOURCE")
	(setq doorFlags::p2cEdges (list PvcKoduKAPAK PvcKoduKAPAK PvcKoduKAPAK PvcKoduKAPAK))
	(setq doorFlags::p2cProfiles (list prfT prfT prfT prfT))
	(setq doorFlags::p2cFrameThick 55)
)
(mapcar '(lambda (x) (set (read (strcat "KKULPC" "_" x "KANATSETS")) KKULPC_AKANATSETS) ) _KSets_typeAList)

(defun KKULPC_BKANATSETS(x z)
	(setq doorFlags::p2cDoorSource "INSOURCE")
	(setq doorFlags::p2cFrameThick 55)
	(setq doorFlags::p2cProfiles (list nil nil nil nil))
)
(mapcar '(lambda (x) (set (read (strcat "KKULPC" "_" x "KANATSETS")) KKULPC_BKANATSETS) ) _KSets_typeBList)
(mapcar '(lambda (x) (set (read (strcat "KKULPC" "_" x "_MAT_LAYER")) "ALUMINIUM_FRAME") ) _KSets_typeBList)

;__________________________________________________________________________________________________________________________________________________________

(defun ICKULP_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "ICKULP" "_" x "KANATSETS")) ICKULP_AKANATSETS) ) _KSets_typeAList)

(defun ICKULP_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "ICKULP" "_" x "KANATSETS")) ICKULP_BKANATSETS) ) _KSets_typeBList)

;__________________________________________________________________________________________________________________________________________________________

(defun OVACIK_AKANATSETS(x z)
	(setq doorFlags::p2cDoorSource "INSOURCE")
	(setq doorFlags::p2cEdges (list PvcKoduKAPAK PvcKoduKAPAK PvcKoduKAPAK PvcKoduKAPAK))
	(setq doorFlags::p2cProfiles (list prfT prfT prfT prfT))
	(setq doorFlags::p2cFrameThick 55)
)
(mapcar '(lambda (x) (set (read (strcat "OVACIK" "_" x "KANATSETS")) OVACIK_AKANATSETS) ) _KSets_typeAList)

(defun OVACIK_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "OVACIK" "_" x "KANATSETS")) OVACIK_BKANATSETS) ) _KSets_typeBList)
(mapcar '(lambda (x) (set (read (strcat "OVACIK" "_" x "_MAT_LAYER")) "ALUMINIUM_FRAME") ) _KSets_typeBList)

;__________________________________________________________________________________________________________________________________________________________

(defun PRFC_AKANATSETS(x z)
	(setq doorFlags::p2cDoorSource "INSOURCE")
	(setq doorFlags::p2cEdges (list PvcKoduKAPAK PvcKoduKAPAK PvcKoduKAPAK PvcKoduKAPAK))
	(setq doorFlags::p2cProfiles (list nil nil nil nil))
	(setq doorFlags::p2cFrameThick 55)
)
(mapcar '(lambda (x) (set (read (strcat "PRFC" "_" x "KANATSETS")) PRFC_AKANATSETS) ) _KSets_typeAList)

(defun PRFC_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("K-" "G-" )) (setq doorFlags::p2cProfiles (list prfKL prfKS prfKS prfKS)))
		((member kulp '("GD" "KD" "D-")) (setq doorFlags::p2cProfiles (list prfKS prfKL prfKS prfKS)))
	)
)
(mapcar '(lambda (x) (set (read (strcat "PRFC" "_" x "KANATSETS")) PRFC_BKANATSETS) ) _KSets_typeBList)
(mapcar '(lambda (x) (set (read (strcat "PRFC" "_" x "_MAT_LAYER")) "ALUMINIUM_FRAME") ) _KSets_typeBList)

;__________________________________________________________________________________________________________________________________________________________

(defun KAPAK108_AKANATSETS(x z)
	(setq doorFlags::p2cDoorSource "INSOURCE")
	(setq doorFlags::p2cEdges (list PvcKoduKAPAK PvcKoduKAPAK PvcKoduKAPAK PvcKoduKAPAK))
	(setq doorFlags::p2cProfiles (list nil nil nil nil))
	(setq doorFlags::p2cFrameThick 55)
)
(mapcar '(lambda (x) (set (read (strcat "KAPAK108" "_" x "KANATSETS")) KAPAK108_AKANATSETS) ) _KSets_typeAList)

(defun KAPAK108_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("G-" "GD")) (setq doorFlags::p2cProfiles (list prfKL prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "KAPAK108" "_" x "KANATSETS")) KAPAK108_BKANATSETS) ) _KSets_typeBList)
(mapcar '(lambda (x) (set (read (strcat "KAPAK108" "_" x "_MAT_LAYER")) "ALUMINIUM_FRAME") ) _KSets_typeBList)

;__________________________________________________________________________________________________________________________________________________________

(defun KAPAK107_AKANATSETS(x z)
	(setq doorFlags::p2cDoorSource "INSOURCE")
	(setq doorFlags::p2cEdges (list PvcKoduKAPAK PvcKoduKAPAK PvcKoduKAPAK PvcKoduKAPAK))
	(setq doorFlags::p2cProfiles (list nil nil nil nil))
	(setq doorFlags::p2cFrameThick 55)
)
(mapcar '(lambda (x) (set (read (strcat "KAPAK107" "_" x "KANATSETS")) KAPAK107_AKANATSETS) ) _KSets_typeAList)

(defun KAPAK107_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "KAPAK107" "_" x "KANATSETS")) KAPAK107_BKANATSETS) ) _KSets_typeBList)
(mapcar '(lambda (x) (set (read (strcat "KAPAK107" "_" x "_MAT_LAYER")) "ALUMINIUM_FRAME") ) _KSets_typeBList)

;__________________________________________________________________________________________________________________________________________________________

(defun KAPAK109_AKANATSETS(x z)
	(setq doorFlags::p2cDoorSource "INSOURCE")
	(setq doorFlags::p2cEdges (list nil nil nil nil))
	(setq doorFlags::p2cProfiles (list prfT prfT prfT prfT))
	(setq doorFlags::p2cFrameThick 55)
)
(mapcar '(lambda (x) (set (read (strcat "KAPAK109" "_" x "KANATSETS")) KAPAK109_AKANATSETS) ) _KSets_typeAList)

(defun KAPAK109_BKANATSETS(x z)
	(setq doorFlags::p2cDoorSource "INSOURCE")
	(setq doorFlags::p2cEdges (list nil nil nil nil))
	(setq doorFlags::p2cProfiles (list prfT prfT prfT prfT))
	(setq doorFlags::p2cFrameThick 55)
)
(mapcar '(lambda (x) (set (read (strcat "KAPAK109" "_" x "KANATSETS")) KAPAK109_BKANATSETS) ) _KSets_typeBList)

;__________________________________________________________________________________________________________________________________________________________

(defun 10387202_AKANATSETS(x z)
	(setq doorFlags::p2cDoorSource "INSOURCE")
	(setq doorFlags::p2cEdges (list PvcKoduKAPAK PvcKoduKAPAK PvcKoduKAPAK PvcKoduKAPAK))
	(setq doorFlags::p2cProfiles (list nil nil nil nil))
	(setq doorFlags::p2cFrameThick 55)
)
(mapcar '(lambda (x) (set (read (strcat "10387202" "_" x "KANATSETS")) 10387202_AKANATSETS) ) _KSets_typeAList)

(defun 10387202_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "10387202" "_" x "KANATSETS")) 10387202_BKANATSETS) ) _KSets_typeBList)
(mapcar '(lambda (x) (set (read (strcat "10387202" "_" x "_MAT_LAYER")) "ALUMINIUM_FRAME") ) _KSets_typeBList)

;__________________________________________________________________________________________________________________________________________________________

(defun 10387206_AKANATSETS(x z)
	(setq doorFlags::p2cDoorSource "INSOURCE")
	(setq doorFlags::p2cEdges (list PvcKoduKAPAK PvcKoduKAPAK PvcKoduKAPAK PvcKoduKAPAK))
	(setq doorFlags::p2cProfiles (list nil nil nil nil))
	(setq doorFlags::p2cFrameThick 55)
)
(mapcar '(lambda (x) (set (read (strcat "10387206" "_" x "KANATSETS")) 10387206_AKANATSETS) ) _KSets_typeAList)

(defun 10387206_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "10387206" "_" x "KANATSETS")) 10387206_BKANATSETS) ) _KSets_typeBList)
(mapcar '(lambda (x) (set (read (strcat "10387206" "_" x "_MAT_LAYER")) "ALUMINIUM_FRAME") ) _KSets_typeBList)

;__________________________________________________________________________________________________________________________________________________________

(defun 10868913_AKANATSETS(x z)
	(setq doorFlags::p2cDoorSource "INSOURCE")
	(setq doorFlags::p2cEdges (list PvcKoduKAPAK PvcKoduKAPAK PvcKoduKAPAK PvcKoduKAPAK))
	(setq doorFlags::p2cProfiles (list nil nil nil nil))
	(setq doorFlags::p2cFrameThick 55)
)
(mapcar '(lambda (x) (set (read (strcat "10868913" "_" x "KANATSETS")) 10868913_AKANATSETS) ) _KSets_typeAList)

(defun 10868913_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "10868913" "_" x "KANATSETS")) 10868913_BKANATSETS) ) _KSets_typeBList)
(mapcar '(lambda (x) (set (read (strcat "10868913" "_" x "_MAT_LAYER")) "ALUMINIUM_FRAME") ) _KSets_typeBList)

;__________________________________________________________________________________________________________________________________________________________

(defun 15147912_AKANATSETS(x z)
	(setq doorFlags::p2cDoorSource "INSOURCE")
	(setq doorFlags::p2cEdges (list PvcKoduKAPAK PvcKoduKAPAK PvcKoduKAPAK PvcKoduKAPAK))
	(setq doorFlags::p2cProfiles (list nil nil nil nil))
	(setq doorFlags::p2cFrameThick 55)
)
(mapcar '(lambda (x) (set (read (strcat "15147912" "_" x "KANATSETS")) 15147912_AKANATSETS) ) _KSets_typeAList)

(defun 15147912_BKANATSETS(x z)
	(setq doorFlags::p2cDoorSource "INSOURCE")
	(setq doorFlags::p2cFrameThick 55)
	(cond 
		((member kulp '("0-" )) (setq doorFlags::p2cProfiles (list prfKS prfKS prfKS prfKS)))
		((member kulp '("D-")) (setq doorFlags::p2cProfiles (list prfKS prfKL prfKS prfKS)))
		(T (setq doorFlags::p2cProfiles (list prfKL prfKS prfKS prfKS)))
	)
)
(mapcar '(lambda (x) (set (read (strcat "15147912" "_" x "KANATSETS")) 15147912_BKANATSETS) ) _KSets_typeBList)
(mapcar '(lambda (x) (set (read (strcat "15147912" "_" x "_MAT_LAYER")) "ALUMINIUM_FRAME") ) _KSets_typeBList)

;__________________________________________________________________________________________________________________________________________________________

(defun MINE_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "MINE" "_" x "KANATSETS")) MINE_AKANATSETS) ) _KSets_typeAList)

;__________________________________________________________________________________________________________________________________________________________

(defun ORCUN_AKANATSETS(x z)
	(setq doorFlags::p2cDoorSource "INSOURCE")
	(setq doorFlags::p2cEdges (list nil PvcKoduKAPAK PvcKoduKAPAK PvcKoduKAPAK))
	(setq doorFlags::p2cFrameThick 55)
)
(mapcar '(lambda (x) (set (read (strcat "ORCUN" "_" x "KANATSETS")) ORCUN_AKANATSETS) ) _KSets_typeAList)

;__________________________________________________________________________________________________________________________________________________________

(defun JMETALPRFL_BKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		((member kulp '("K-" "KD")) (setq doorFlags::p2cEdges (list PvcKoduProfil PvcKoduKAPAK PvcKoduKAPAK PvcKoduKAPAK)))
		((member kulp '("G-" "GD")) (setq doorFlags::p2cEdges (list PvcKoduKAPAK PvcKoduKAPAK PvcKoduProfil PvcKoduKAPAK)))
		((member kulp '("D-")) (setq doorFlags::p2cEdges (list PvcKoduKAPAK PvcKoduProfil PvcKoduKAPAK PvcKoduKAPAK)))
	)
	(cond 
		((member kulp '("0-")) (setq doorFlags::p2cProfiles (list nil nil nil nil)))
		((member kulp '("K-" "KD" )) (setq doorFlags::p2cProfiles (list prfA nil nil nil)))
		((member kulp '("G-" "GD")) (setq doorFlags::p2cProfiles (list nil nil prfA nil)))
		((member kulp '("D-")) (setq doorFlags::p2cProfiles (list nil prfA nil nil)))
	)
)
(mapcar '(lambda (x) (set (read (strcat "JMETALPRFL" "_" x "KANATSETS")) JMETALPRFL_BKANATSETS) ) _KSets_typeBList)
(mapcar '(lambda (x) (set (read (strcat "JMETALPRFL" "_" x "_MAT_LAYER")) "ALUMINIUM_FRAME") ) _KSets_typeBList)

;__________________________________________________________________________________________________________________________________________________________

(defun JAHSAPPRFL_BKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		((member kulp '("K-" "KD")) (setq doorFlags::p2cEdges (list PvcKoduProfil PvcKoduKAPAK PvcKoduKAPAK PvcKoduKAPAK)))
		((member kulp '("G-" "GD")) (setq doorFlags::p2cEdges (list PvcKoduKAPAK PvcKoduKAPAK PvcKoduProfil PvcKoduKAPAK)))
		((member kulp '("D-")) (setq doorFlags::p2cEdges (list PvcKoduKAPAK PvcKoduProfil PvcKoduKAPAK PvcKoduKAPAK)))
	)
	(cond 
		((member kulp '("0-")) (setq doorFlags::p2cProfiles (list nil nil nil nil)))
		((member kulp '("K-" "KD" )) (setq doorFlags::p2cProfiles (list prfA nil nil nil)))
		((member kulp '("G-" "GD")) (setq doorFlags::p2cProfiles (list nil nil prfA nil)))
		((member kulp '("D-")) (setq doorFlags::p2cProfiles (list nil prfA nil nil)))
	)
)
(mapcar '(lambda (x) (set (read (strcat "JAHSAPPRFL" "_" x "KANATSETS")) JAHSAPPRFL_BKANATSETS) ) _KSets_typeBList)
(mapcar '(lambda (x) (set (read (strcat "JAHSAPPRFL" "_" x "_MAT_LAYER")) "ALUMINIUM_FRAME") ) _KSets_typeBList)

;__________________________________________________________________________________________________________________________________________________________

(defun JMETALPRFL_BKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		((member kulp '("K-" "KD")) (setq doorFlags::p2cEdges (list PvcKoduProfil PvcKoduKAPAK PvcKoduKAPAK PvcKoduKAPAK)))
		((member kulp '("G-" "GD")) (setq doorFlags::p2cEdges (list PvcKoduKAPAK PvcKoduKAPAK PvcKoduProfil PvcKoduKAPAK)))
		((member kulp '("D-")) (setq doorFlags::p2cEdges (list PvcKoduKAPAK PvcKoduProfil PvcKoduKAPAK PvcKoduKAPAK)))
	)
	(cond 
		((member kulp '("0-")) (setq doorFlags::p2cProfiles (list nil nil nil nil)))
		((member kulp '("K-" "KD" )) (setq doorFlags::p2cProfiles (list prfA nil nil nil)))
		((member kulp '("G-" "GD")) (setq doorFlags::p2cProfiles (list nil nil prfA nil)))
		((member kulp '("D-")) (setq doorFlags::p2cProfiles (list nil prfA nil nil)))
	)
)
(mapcar '(lambda (x) (set (read (strcat "JAHSAPPRFL" "_" x "KANATSETS")) JMETALPRFL_BKANATSETS) ) _KSets_typeBList)

;__________________________________________________________________________________________________________________________________________________________

(defun JMTLBOYPRFL_BKANATSETS(x z)
	(setq doorFlags::p2cDoorSource "INSOURCE")
	(setq doorFlags::p2cFrameThick 55)
	(cond 
		((member kulp '("0-" )) (setq doorFlags::p2cEdges (list PvcKoduKAPAK PvcKoduKAPAK PvcKoduKAPAK PvcKoduKAPAK)))
		((member kulp '("K-" "G-" )) (setq doorFlags::p2cEdges (list PvcKoduProfil PvcKoduKAPAK PvcKoduKAPAK PvcKoduKAPAK)))
		((member kulp '("GD" "KD" "D-")) (setq doorFlags::p2cEdges (list PvcKoduKAPAK PvcKoduProfil PvcKoduKAPAK PvcKoduKAPAK)))
	)
	(cond 
		((member kulp '("0-" )) (setq doorFlags::p2cProfiles (list nil nil nil nil)))
		((member kulp '("K-" "G-" )) (setq doorFlags::p2cProfiles (list prfA nil nil nil)))
		((member kulp '("GD" "KD" "D-")) (setq doorFlags::p2cProfiles (list nil prfA nil nil)))
	)
)
(mapcar '(lambda (x) (set (read (strcat "JMTLBOYPRFL" "_" x "KANATSETS")) JMTLBOYPRFL_BKANATSETS) ) _KSets_typeBList)
(mapcar '(lambda (x) (set (read (strcat "JMTLBOYPRFL" "_" x "_MAT_LAYER")) "ALUMINIUM_FRAME") ) _KSets_typeBList)

;__________________________________________________________________________________________________________________________________________________________

(defun LBOYPRFL_BKANATSETS(x z)
	(setq doorFlags::p2cDoorSource "INSOURCE")
	(setq doorFlags::p2cFrameThick 55)
	(cond 
		((member kulp '("0-" )) (setq doorFlags::p2cEdges (list PvcKoduKAPAK PvcKoduKAPAK PvcKoduKAPAK PvcKoduKAPAK)))
		((member kulp '("K-" "KD" )) (setq doorFlags::p2cEdges (list PvcKoduProfil PvcKoduKAPAK PvcKoduKAPAK PvcKoduKAPAK)))
		((member kulp '("G-" "GD")) (setq doorFlags::p2cEdges (list PvcKoduKAPAK PvcKoduKAPAK PvcKoduProfil PvcKoduKAPAK)))
		((member kulp '("D-")) (setq doorFlags::p2cEdges (list PvcKoduKAPAK PvcKoduProfil PvcKoduKAPAK PvcKoduKAPAK)))
	)
	(cond 
		((member kulp '("0-" )) (setq doorFlags::p2cProfileHandles (list nil nil nil nil)))
		((member kulp '("K-" "KD")) (setq doorFlags::p2cProfileHandles (list entT2 nil nil nil)))
		((member kulp '("G-" "GD")) (setq doorFlags::p2cProfileHandles (list nil nil entT2 nil)))
		((member kulp '("D-")) (setq doorFlags::p2cProfileHandles (list nil entT2 nil nil)))
	)
)
(mapcar '(lambda (x) (set (read (strcat "LBOYPRFL" "_" x "KANATSETS")) LBOYPRFL_BKANATSETS) ) _KSets_typeBList)
(mapcar '(lambda (x) (set (read (strcat "LBOYPRFL" "_" x "_MAT_LAYER")) "ALUMINIUM_FRAME") ) _KSets_typeBList)

;__________________________________________________________________________________________________________________________________________________________

(defun T300PRFL_BKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		((member kulp '("K-" "KD")) (setq doorFlags::p2cEdges (list PvcKoduProfil PvcKoduKAPAK PvcKoduKAPAK PvcKoduKAPAK)))
		((member kulp '("G-" "GD")) (setq doorFlags::p2cEdges (list PvcKoduProfil PvcKoduKAPAK PvcKoduKAPAK PvcKoduKAPAK)))
		((member kulp '("D-")) (setq doorFlags::p2cEdges (list PvcKoduKAPAK PvcKoduProfil PvcKoduKAPAK PvcKoduKAPAK)))
	)
	(cond 
		((member kulp '("0-" )) (setq doorFlags::p2cProfileHandles (list nil nil nil nil)))
		((member kulp '("K-" "KD")) (setq doorFlags::p2cProfileHandles (list entT4 nil nil nil)))
		((member kulp '("G-" "GD")) (setq doorFlags::p2cProfileHandles (list nil nil entT4 nil)))
		((member kulp '("D-")) (setq doorFlags::p2cProfileHandles (list nil entT4 nil nil)))
	)
)
(mapcar '(lambda (x) (set (read (strcat "T300PRFL" "_" x "KANATSETS")) T300PRFL_BKANATSETS) ) _KSets_typeBList)
(mapcar '(lambda (x) (set (read (strcat "T300PRFL" "_" x "_MAT_LAYER")) "ALUMINIUM_FRAME") ) _KSets_typeBList)

;__________________________________________________________________________________________________________________________________________________________

(defun T400PRFL_BKANATSETS(x z)
	(setq doorFlags::p2cDoorSource "INSOURCE")
	(setq doorFlags::p2cFrameThick 55)
	(cond 
		((member kulp '("0-")) (setq doorFlags::p2cEdges (list PvcKoduKAPAK PvcKoduKAPAK PvcKoduKAPAK PvcKoduKAPAK)))
		((member kulp '("K-" "KD")) (setq doorFlags::p2cEdges (list PvcKoduProfil PvcKoduKAPAK PvcKoduKAPAK PvcKoduKAPAK)))
		((member kulp '("G-" "GD")) (setq doorFlags::p2cEdges (list PvcKoduProfil PvcKoduKAPAK PvcKoduKAPAK PvcKoduKAPAK)))
		((member kulp '("D-")) (setq doorFlags::p2cEdges (list PvcKoduKAPAK PvcKoduProfil PvcKoduKAPAK PvcKoduKAPAK)))
	)
	(cond 
		((member kulp '("0-" )) (setq doorFlags::p2cProfileHandles (list nil nil nil nil)))
		((member kulp '("K-" "KD")) (setq doorFlags::p2cProfileHandles (list entT4 nil nil nil)))
		((member kulp '("G-" "GD")) (setq doorFlags::p2cProfileHandles (list nil nil entT4 nil)))
		((member kulp '("D-")) (setq doorFlags::p2cProfileHandles (list nil entT4 nil nil)))
	)
)
(mapcar '(lambda (x) (set (read (strcat "T400PRFL" "_" x "KANATSETS")) T400PRFL_BKANATSETS) ) _KSets_typeBList)
(mapcar '(lambda (x) (set (read (strcat "T400PRFL" "_" x "_MAT_LAYER")) "ALUMINIUM_FRAME") ) _KSets_typeBList)

;__________________________________________________________________________________________________________________________________________________________

(defun ALMPRFKULP_BKANATSETS(x z)
	(setq doorFlags::p2cFrameThick 55)
	(setq doorFlags::p2cProfiles (list nil nil nil nil))	
)
(mapcar '(lambda (x) (set (read (strcat "ALMPRFKULP" "_" x "KANATSETS")) ALMPRFKULP_BKANATSETS) ) _KSets_typeBList)
(mapcar '(lambda (x) (set (read (strcat "ALMPRFKULP" "_" x "_MAT_LAYER")) "ALUMINIUM_FRAME") ) _KSets_typeBList)

(defun ALUCAMPRFL2_BKANATSETS(x z)
	(setq doorFlags::p2cFrameThick 55)
	(setq doorFlags::p2cProfiles (list nil nil nil nil))
)
(mapcar '(lambda (x) (set (read (strcat "ALUCAMPRFL2" "_" x "KANATSETS")) ALUCAMPRFL2_BKANATSETS) ) _KSets_typeBList)
(mapcar '(lambda (x) (set (read (strcat "ALUCAMPRFL2" "_" x "_MAT_LAYER")) "ALUMINIUM_FRAME") ) _KSets_typeBList)

(defun ALUCAMPRFL_BKANATSETS(x z)
	(setq doorFlags::p2cFrameThick 55)
	(setq doorFlags::p2cProfiles (list nil nil nil nil))
)
(mapcar '(lambda (x) (set (read (strcat "ALUCAMPRFL2" "_" x "KANATSETS")) ALUCAMPRFL2_BKANATSETS) ) _KSets_typeBList)
(mapcar '(lambda (x) (set (read (strcat "ALUCAMPRFL2" "_" x "_MAT_LAYER")) "ALUMINIUM_FRAME") ) _KSets_typeBList)

;__________________________________________________________________________________________________________________________________________________________



;DETAYLANDIRILMAYAN KAPAKLAR
;__________________________________________________________________________________________________________________________________________________________
;__________________________________________________________________________________________________________________________________________________________
(defun CMKPK100_SETS()(setq doorFlags::p2cDoorSource "INSOURCE")(setq doorFlags::p2cEdges (list PvcKoduKAPAK PvcKoduKAPAK PvcKoduKAPAK PvcKoduKAPAK))(setq doorFlags::p2cFrameThick 55))
(defun CMKPK101_SETS()(setq doorFlags::p2cDoorSource "INSOURCE")(setq doorFlags::p2cEdges (list PvcKoduKAPAK PvcKoduKAPAK PvcKoduKAPAK PvcKoduKAPAK))(setq doorFlags::p2cFrameThick 55))
(defun CMKPK102_SETS()(setq doorFlags::p2cDoorSource "INSOURCE")(setq doorFlags::p2cEdges (list PvcKoduKAPAK PvcKoduKAPAK PvcKoduKAPAK PvcKoduKAPAK))(setq doorFlags::p2cFrameThick 55))
(defun CMKPK103_SETS()(setq doorFlags::p2cDoorSource "INSOURCE")(setq doorFlags::p2cEdges (list PvcKoduKAPAK PvcKoduKAPAK PvcKoduKAPAK PvcKoduKAPAK))(setq doorFlags::p2cFrameThick 55))
(defun CMKPK104_SETS()(setq doorFlags::p2cDoorSource "INSOURCE")(setq doorFlags::p2cEdges (list PvcKoduKAPAK PvcKoduKAPAK PvcKoduKAPAK PvcKoduKAPAK))(setq doorFlags::p2cFrameThick 55))
(defun CMKPK105_SETS()(setq doorFlags::p2cDoorSource "INSOURCE")(setq doorFlags::p2cEdges (list PvcKoduKAPAK PvcKoduKAPAK PvcKoduKAPAK PvcKoduKAPAK))(setq doorFlags::p2cFrameThick 55))
(defun CMKPK106_SETS()(setq doorFlags::p2cDoorSource "INSOURCE")(setq doorFlags::p2cEdges (list PvcKoduKAPAK PvcKoduKAPAK PvcKoduKAPAK PvcKoduKAPAK))(setq doorFlags::p2cFrameThick 55))
(defun CTL08_SETS()(setq doorFlags::p2cDoorSource "INSOURCE")(setq doorFlags::p2cEdges (list PvcKoduKAPAK PvcKoduKAPAK PvcKoduKAPAK PvcKoduKAPAK))(setq doorFlags::p2cFrameThick 55))
(defun DISCITA_SETS()(setq doorFlags::p2cDoorSource "INSOURCE")(setq doorFlags::p2cEdges (list PvcKoduKAPAK PvcKoduKAPAK PvcKoduKAPAK PvcKoduKAPAK))(setq doorFlags::p2cFrameThick 55))
(defun CITALI3_SETS()(setq doorFlags::p2cDoorSource "INSOURCE")(setq doorFlags::p2cEdges (list PvcKoduKAPAK PvcKoduKAPAK PvcKoduKAPAK PvcKoduKAPAK))(setq doorFlags::p2cFrameThick 55))
(defun CITALI5_SETS()(setq doorFlags::p2cDoorSource "INSOURCE")(setq doorFlags::p2cEdges (list PvcKoduKAPAK PvcKoduKAPAK PvcKoduKAPAK PvcKoduKAPAK))(setq doorFlags::p2cFrameThick 55))
(defun ICCITALI_SETS()(setq doorFlags::p2cDoorSource "INSOURCE")(setq doorFlags::p2cEdges (list PvcKoduKAPAK PvcKoduKAPAK PvcKoduKAPAK PvcKoduKAPAK))(setq doorFlags::p2cFrameThick 55))
(defun CTL33X33_SETS()(setq doorFlags::p2cDoorSource "INSOURCE")(setq doorFlags::p2cEdges (list PvcKoduKAPAK PvcKoduKAPAK PvcKoduKAPAK PvcKoduKAPAK))(setq doorFlags::p2cFrameThick 55))
(defun CTL55X33_SETS()(setq doorFlags::p2cDoorSource "INSOURCE")(setq doorFlags::p2cEdges (list PvcKoduKAPAK PvcKoduKAPAK PvcKoduKAPAK PvcKoduKAPAK))(setq doorFlags::p2cFrameThick 55))
(defun CTL55X55_SETS()(setq doorFlags::p2cDoorSource "INSOURCE")(setq doorFlags::p2cEdges (list PvcKoduKAPAK PvcKoduKAPAK PvcKoduKAPAK PvcKoduKAPAK))(setq doorFlags::p2cFrameThick 55))
(defun CTL5X5_SETS()(setq doorFlags::p2cDoorSource "INSOURCE")(setq doorFlags::p2cEdges (list PvcKoduKAPAK PvcKoduKAPAK PvcKoduKAPAK PvcKoduKAPAK))(setq doorFlags::p2cFrameThick 55))
(defun CTL66_SETS()(setq doorFlags::p2cDoorSource "INSOURCE")(setq doorFlags::p2cEdges (list PvcKoduKAPAK PvcKoduKAPAK PvcKoduKAPAK PvcKoduKAPAK))(setq doorFlags::p2cFrameThick 55))
(defun CTL77_SETS()(setq doorFlags::p2cDoorSource "INSOURCE")(setq doorFlags::p2cEdges (list PvcKoduKAPAK PvcKoduKAPAK PvcKoduKAPAK PvcKoduKAPAK))(setq doorFlags::p2cFrameThick 55))
(defun CTL88_SETS()(setq doorFlags::p2cDoorSource "INSOURCE")(setq doorFlags::p2cEdges (list PvcKoduKAPAK PvcKoduKAPAK PvcKoduKAPAK PvcKoduKAPAK))(setq doorFlags::p2cFrameThick 55))
(defun CTL858_SETS()(setq doorFlags::p2cDoorSource "INSOURCE")(setq doorFlags::p2cEdges (list PvcKoduKAPAK PvcKoduKAPAK PvcKoduKAPAK PvcKoduKAPAK))(setq doorFlags::p2cFrameThick 55))
(defun CTL66X15_SETS()(setq doorFlags::p2cDoorSource "INSOURCE")(setq doorFlags::p2cEdges (list PvcKoduKAPAK PvcKoduKAPAK PvcKoduKAPAK PvcKoduKAPAK))(setq doorFlags::p2cFrameThick 55))
(defun CTLSRT_SETS()(setq doorFlags::p2cDoorSource "INSOURCE")(setq doorFlags::p2cEdges (list PvcKoduKAPAK PvcKoduKAPAK PvcKoduKAPAK PvcKoduKAPAK))(setq doorFlags::p2cFrameThick 55))
(defun PAHCITA_SETS()(setq doorFlags::p2cDoorSource "INSOURCE")(setq doorFlags::p2cEdges (list PvcKoduKAPAK PvcKoduKAPAK PvcKoduKAPAK PvcKoduKAPAK))(setq doorFlags::p2cFrameThick 55))
(defun CTL6P_SETS()(setq doorFlags::p2cDoorSource "INSOURCE")(setq doorFlags::p2cEdges (list PvcKoduKAPAK PvcKoduKAPAK PvcKoduKAPAK PvcKoduKAPAK))(setq doorFlags::p2cFrameThick 55))
(defun MRDCITA_SETS()(setq doorFlags::p2cDoorSource "INSOURCE")(setq doorFlags::p2cEdges (list PvcKoduKAPAK PvcKoduKAPAK PvcKoduKAPAK PvcKoduKAPAK))(setq doorFlags::p2cFrameThick 55))
(defun KMR55_SETS()(setq doorFlags::p2cDoorSource "INSOURCE")(setq doorFlags::p2cEdges (list PvcKoduKAPAK PvcKoduKAPAK PvcKoduKAPAK PvcKoduKAPAK))(setq doorFlags::p2cFrameThick 55))
(defun YUVCITA_SETS()(setq doorFlags::p2cDoorSource "INSOURCE")(setq doorFlags::p2cEdges (list PvcKoduKAPAK PvcKoduKAPAK PvcKoduKAPAK PvcKoduKAPAK))(setq doorFlags::p2cFrameThick 55))
(defun 2RADYUS_SETS()(setq doorFlags::p2cDoorSource "INSOURCE")(setq doorFlags::p2cEdges (list PvcKoduKAPAK PvcKoduKAPAK PvcKoduKAPAK PvcKoduKAPAK))(setq doorFlags::p2cFrameThick 55))
(defun 4RADYUS_SETS()(setq doorFlags::p2cDoorSource "INSOURCE")(setq doorFlags::p2cEdges (list PvcKoduKAPAK PvcKoduKAPAK PvcKoduKAPAK PvcKoduKAPAK))(setq doorFlags::p2cFrameThick 55))
(defun SOFT_SETS()(setq doorFlags::p2cDoorSource "INSOURCE")(setq doorFlags::p2cEdges (list PvcKoduKAPAK PvcKoduKAPAK PvcKoduKAPAK PvcKoduKAPAK))(setq doorFlags::p2cFrameThick 55))
(defun SOFT2_SETS()(setq doorFlags::p2cDoorSource "INSOURCE")(setq doorFlags::p2cEdges (list PvcKoduKAPAK PvcKoduKAPAK PvcKoduKAPAK PvcKoduKAPAK))(setq doorFlags::p2cFrameThick 55))
(defun B001_SETS()(setq doorFlags::p2cDoorSource "INSOURCE")(setq doorFlags::p2cEdges (list PvcKoduKAPAK PvcKoduKAPAK PvcKoduKAPAK PvcKoduKAPAK))(setq doorFlags::p2cFrameThick 55))
(defun B002_SETS()(setq doorFlags::p2cDoorSource "INSOURCE")(setq doorFlags::p2cEdges (list PvcKoduKAPAK PvcKoduKAPAK PvcKoduKAPAK PvcKoduKAPAK))(setq doorFlags::p2cFrameThick 55))
(defun B003_SETS()(setq doorFlags::p2cDoorSource "INSOURCE")(setq doorFlags::p2cEdges (list PvcKoduKAPAK PvcKoduKAPAK PvcKoduKAPAK PvcKoduKAPAK))(setq doorFlags::p2cFrameThick 55))
(defun B004_SETS()(setq doorFlags::p2cDoorSource "INSOURCE")(setq doorFlags::p2cEdges (list PvcKoduKAPAK PvcKoduKAPAK PvcKoduKAPAK PvcKoduKAPAK))(setq doorFlags::p2cFrameThick 55))
(defun K05D_SETS()(setq doorFlags::p2cDoorSource "INSOURCE")(setq doorFlags::p2cEdges (list PvcKoduKAPAK PvcKoduKAPAK PvcKoduKAPAK PvcKoduKAPAK))(setq doorFlags::p2cFrameThick 55))
(defun B010_SETS()(setq doorFlags::p2cDoorSource "INSOURCE")(setq doorFlags::p2cEdges (list PvcKoduKAPAK PvcKoduKAPAK PvcKoduKAPAK PvcKoduKAPAK))(setq doorFlags::p2cFrameThick 55))
(defun B001Y_SETS()(setq doorFlags::p2cDoorSource "INSOURCE")(setq doorFlags::p2cEdges (list PvcKoduKAPAK PvcKoduKAPAK PvcKoduKAPAK PvcKoduKAPAK))(setq doorFlags::p2cFrameThick 55))
(defun B002Y_SETS()(setq doorFlags::p2cDoorSource "INSOURCE")(setq doorFlags::p2cEdges (list PvcKoduKAPAK PvcKoduKAPAK PvcKoduKAPAK PvcKoduKAPAK))(setq doorFlags::p2cFrameThick 55))
(defun B003Y_SETS()(setq doorFlags::p2cDoorSource "INSOURCE")(setq doorFlags::p2cEdges (list PvcKoduKAPAK PvcKoduKAPAK PvcKoduKAPAK PvcKoduKAPAK))(setq doorFlags::p2cFrameThick 55))
(defun B004Y_SETS()(setq doorFlags::p2cDoorSource "INSOURCE")(setq doorFlags::p2cEdges (list PvcKoduKAPAK PvcKoduKAPAK PvcKoduKAPAK PvcKoduKAPAK))(setq doorFlags::p2cFrameThick 55))
(defun K05Y_SETS()(setq doorFlags::p2cDoorSource "INSOURCE")(setq doorFlags::p2cEdges (list PvcKoduKAPAK PvcKoduKAPAK PvcKoduKAPAK PvcKoduKAPAK))(setq doorFlags::p2cFrameThick 55))
(defun B010Y_SETS()(setq doorFlags::p2cDoorSource "INSOURCE")(setq doorFlags::p2cEdges (list PvcKoduKAPAK PvcKoduKAPAK PvcKoduKAPAK PvcKoduKAPAK))(setq doorFlags::p2cFrameThick 55))
(defun PLT81_SETS()(setq doorFlags::p2cDoorSource "INSOURCE")(setq doorFlags::p2cEdges (list PvcKoduKAPAK PvcKoduKAPAK PvcKoduKAPAK PvcKoduKAPAK))(setq doorFlags::p2cFrameThick 55))
(defun PLT82_SETS()(setq doorFlags::p2cDoorSource "INSOURCE")(setq doorFlags::p2cEdges (list PvcKoduKAPAK PvcKoduKAPAK PvcKoduKAPAK PvcKoduKAPAK))(setq doorFlags::p2cFrameThick 55))
(defun PLT83_SETS()(setq doorFlags::p2cDoorSource "INSOURCE")(setq doorFlags::p2cEdges (list PvcKoduKAPAK PvcKoduKAPAK PvcKoduKAPAK PvcKoduKAPAK))(setq doorFlags::p2cFrameThick 55))
(defun PLT84_SETS()(setq doorFlags::p2cDoorSource "INSOURCE")(setq doorFlags::p2cEdges (list PvcKoduKAPAK PvcKoduKAPAK PvcKoduKAPAK PvcKoduKAPAK))(setq doorFlags::p2cFrameThick 55))
(defun PLT85_SETS()(setq doorFlags::p2cDoorSource "INSOURCE")(setq doorFlags::p2cEdges (list PvcKoduKAPAK PvcKoduKAPAK PvcKoduKAPAK PvcKoduKAPAK))(setq doorFlags::p2cFrameThick 55))
(defun PLT82Y_SETS()(setq doorFlags::p2cDoorSource "INSOURCE")(setq doorFlags::p2cEdges (list PvcKoduKAPAK PvcKoduKAPAK PvcKoduKAPAK PvcKoduKAPAK))(setq doorFlags::p2cFrameThick 55))
(defun PLT83Y_SETS()(setq doorFlags::p2cDoorSource "INSOURCE")(setq doorFlags::p2cEdges (list PvcKoduKAPAK PvcKoduKAPAK PvcKoduKAPAK PvcKoduKAPAK))(setq doorFlags::p2cFrameThick 55))
(defun PLT84Y_SETS()(setq doorFlags::p2cDoorSource "INSOURCE")(setq doorFlags::p2cEdges (list PvcKoduKAPAK PvcKoduKAPAK PvcKoduKAPAK PvcKoduKAPAK))(setq doorFlags::p2cFrameThick 55))
(defun PLT85Y_SETS()(setq doorFlags::p2cDoorSource "INSOURCE")(setq doorFlags::p2cEdges (list PvcKoduKAPAK PvcKoduKAPAK PvcKoduKAPAK PvcKoduKAPAK))(setq doorFlags::p2cFrameThick 55))
(defun 1801_SETS()(setq doorFlags::p2cDoorSource "INSOURCE")(setq doorFlags::p2cEdges (list PvcKoduKAPAK PvcKoduKAPAK PvcKoduKAPAK PvcKoduKAPAK))(setq doorFlags::p2cFrameThick 55))
(defun 1804_SETS()(setq doorFlags::p2cDoorSource "INSOURCE")(setq doorFlags::p2cEdges (list PvcKoduKAPAK PvcKoduKAPAK PvcKoduKAPAK PvcKoduKAPAK))(setq doorFlags::p2cFrameThick 55))
(defun 1806_SETS()(setq doorFlags::p2cDoorSource "INSOURCE")(setq doorFlags::p2cEdges (list PvcKoduKAPAK PvcKoduKAPAK PvcKoduKAPAK PvcKoduKAPAK))(setq doorFlags::p2cFrameThick 55))
(defun 1807_SETS()(setq doorFlags::p2cDoorSource "INSOURCE")(setq doorFlags::p2cEdges (list PvcKoduKAPAK PvcKoduKAPAK PvcKoduKAPAK PvcKoduKAPAK))(setq doorFlags::p2cFrameThick 55))
(defun 1808_SETS()(setq doorFlags::p2cDoorSource "INSOURCE")(setq doorFlags::p2cEdges (list PvcKoduKAPAK PvcKoduKAPAK PvcKoduKAPAK PvcKoduKAPAK))(setq doorFlags::p2cFrameThick 55))
(defun 1814_SETS()(setq doorFlags::p2cDoorSource "INSOURCE")(setq doorFlags::p2cEdges (list PvcKoduKAPAK PvcKoduKAPAK PvcKoduKAPAK PvcKoduKAPAK))(setq doorFlags::p2cFrameThick 55))
(defun 2202_SETS()(setq doorFlags::p2cDoorSource "INSOURCE")(setq doorFlags::p2cEdges (list PvcKoduKAPAK PvcKoduKAPAK PvcKoduKAPAK PvcKoduKAPAK))(setq doorFlags::p2cFrameThick 55))
(defun 2203_SETS()(setq doorFlags::p2cDoorSource "INSOURCE")(setq doorFlags::p2cEdges (list PvcKoduKAPAK PvcKoduKAPAK PvcKoduKAPAK PvcKoduKAPAK))(setq doorFlags::p2cFrameThick 55))
(defun 2204_SETS()(setq doorFlags::p2cDoorSource "INSOURCE")(setq doorFlags::p2cEdges (list PvcKoduKAPAK PvcKoduKAPAK PvcKoduKAPAK PvcKoduKAPAK))(setq doorFlags::p2cFrameThick 55))
(defun 2205_SETS()(setq doorFlags::p2cDoorSource "INSOURCE")(setq doorFlags::p2cEdges (list PvcKoduKAPAK PvcKoduKAPAK PvcKoduKAPAK PvcKoduKAPAK))(setq doorFlags::p2cFrameThick 55))
(defun 2206_SETS()(setq doorFlags::p2cDoorSource "INSOURCE")(setq doorFlags::p2cEdges (list PvcKoduKAPAK PvcKoduKAPAK PvcKoduKAPAK PvcKoduKAPAK))(setq doorFlags::p2cFrameThick 55))
(defun 2207_SETS()(setq doorFlags::p2cDoorSource "INSOURCE")(setq doorFlags::p2cEdges (list PvcKoduKAPAK PvcKoduKAPAK PvcKoduKAPAK PvcKoduKAPAK))(setq doorFlags::p2cFrameThick 55))
(defun 2208_SETS()(setq doorFlags::p2cDoorSource "INSOURCE")(setq doorFlags::p2cEdges (list PvcKoduKAPAK PvcKoduKAPAK PvcKoduKAPAK PvcKoduKAPAK))(setq doorFlags::p2cFrameThick 55))
(defun 2209_SETS()(setq doorFlags::p2cDoorSource "INSOURCE")(setq doorFlags::p2cEdges (list PvcKoduKAPAK PvcKoduKAPAK PvcKoduKAPAK PvcKoduKAPAK))(setq doorFlags::p2cFrameThick 55))
(defun 2501_SETS()(setq doorFlags::p2cDoorSource "INSOURCE")(setq doorFlags::p2cEdges (list PvcKoduKAPAK PvcKoduKAPAK PvcKoduKAPAK PvcKoduKAPAK))(setq doorFlags::p2cFrameThick 55))
(defun 2502_SETS()(setq doorFlags::p2cDoorSource "INSOURCE")(setq doorFlags::p2cEdges (list PvcKoduKAPAK PvcKoduKAPAK PvcKoduKAPAK PvcKoduKAPAK))(setq doorFlags::p2cFrameThick 55))
(defun 2503_SETS()(setq doorFlags::p2cDoorSource "INSOURCE")(setq doorFlags::p2cEdges (list PvcKoduKAPAK PvcKoduKAPAK PvcKoduKAPAK PvcKoduKAPAK))(setq doorFlags::p2cFrameThick 55))
(defun 2505_SETS()(setq doorFlags::p2cDoorSource "INSOURCE")(setq doorFlags::p2cEdges (list PvcKoduKAPAK PvcKoduKAPAK PvcKoduKAPAK PvcKoduKAPAK))(setq doorFlags::p2cFrameThick 55))
(defun 2507_SETS()(setq doorFlags::p2cDoorSource "INSOURCE")(setq doorFlags::p2cEdges (list PvcKoduKAPAK PvcKoduKAPAK PvcKoduKAPAK PvcKoduKAPAK))(setq doorFlags::p2cFrameThick 55))
(defun 1088X1084_SETS()(setq doorFlags::p2cDoorSource "INSOURCE")(setq doorFlags::p2cEdges (list PvcKoduKAPAK PvcKoduKAPAK PvcKoduKAPAK PvcKoduKAPAK))(setq doorFlags::p2cFrameThick 55))
(defun 2202X1084_SETS()(setq doorFlags::p2cDoorSource "INSOURCE")(setq doorFlags::p2cEdges (list PvcKoduKAPAK PvcKoduKAPAK PvcKoduKAPAK PvcKoduKAPAK))(setq doorFlags::p2cFrameThick 55))
(defun 2203X1084_SETS()(setq doorFlags::p2cDoorSource "INSOURCE")(setq doorFlags::p2cEdges (list PvcKoduKAPAK PvcKoduKAPAK PvcKoduKAPAK PvcKoduKAPAK))(setq doorFlags::p2cFrameThick 55))
(defun 9001_SETS()(setq doorFlags::p2cDoorSource "INSOURCE")(setq doorFlags::p2cEdges (list PvcKoduKAPAK PvcKoduKAPAK PvcKoduKAPAK PvcKoduKAPAK))(setq doorFlags::p2cFrameThick 55))
(defun 9002_SETS()(setq doorFlags::p2cDoorSource "INSOURCE")(setq doorFlags::p2cEdges (list PvcKoduKAPAK PvcKoduKAPAK PvcKoduKAPAK PvcKoduKAPAK))(setq doorFlags::p2cFrameThick 55))
(defun 9003_SETS()(setq doorFlags::p2cDoorSource "INSOURCE")(setq doorFlags::p2cEdges (list PvcKoduKAPAK PvcKoduKAPAK PvcKoduKAPAK PvcKoduKAPAK))(setq doorFlags::p2cFrameThick 55))
(defun 9004_SETS()(setq doorFlags::p2cDoorSource "INSOURCE")(setq doorFlags::p2cEdges (list PvcKoduKAPAK PvcKoduKAPAK PvcKoduKAPAK PvcKoduKAPAK))(setq doorFlags::p2cFrameThick 55))
(defun 9005_SETS()(setq doorFlags::p2cDoorSource "INSOURCE")(setq doorFlags::p2cEdges (list PvcKoduKAPAK PvcKoduKAPAK PvcKoduKAPAK PvcKoduKAPAK))(setq doorFlags::p2cFrameThick 55))
(defun 9006_SETS()(setq doorFlags::p2cDoorSource "INSOURCE")(setq doorFlags::p2cEdges (list PvcKoduKAPAK PvcKoduKAPAK PvcKoduKAPAK PvcKoduKAPAK))(setq doorFlags::p2cFrameThick 55))
(defun 9007_SETS()(setq doorFlags::p2cDoorSource "INSOURCE")(setq doorFlags::p2cEdges (list PvcKoduKAPAK PvcKoduKAPAK PvcKoduKAPAK PvcKoduKAPAK))(setq doorFlags::p2cFrameThick 55))
(defun 9008_SETS()(setq doorFlags::p2cDoorSource "INSOURCE")(setq doorFlags::p2cEdges (list PvcKoduKAPAK PvcKoduKAPAK PvcKoduKAPAK PvcKoduKAPAK))(setq doorFlags::p2cFrameThick 55))
(defun 9009_SETS()(setq doorFlags::p2cDoorSource "INSOURCE")(setq doorFlags::p2cEdges (list PvcKoduKAPAK PvcKoduKAPAK PvcKoduKAPAK PvcKoduKAPAK))(setq doorFlags::p2cFrameThick 55))
(defun 9010_SETS()(setq doorFlags::p2cDoorSource "INSOURCE")(setq doorFlags::p2cEdges (list PvcKoduKAPAK PvcKoduKAPAK PvcKoduKAPAK PvcKoduKAPAK))(setq doorFlags::p2cFrameThick 55))
(defun 9011_SETS()(setq doorFlags::p2cDoorSource "INSOURCE")(setq doorFlags::p2cEdges (list PvcKoduKAPAK PvcKoduKAPAK PvcKoduKAPAK PvcKoduKAPAK))(setq doorFlags::p2cFrameThick 55))
(defun 9012_SETS()(setq doorFlags::p2cDoorSource "INSOURCE")(setq doorFlags::p2cEdges (list PvcKoduKAPAK PvcKoduKAPAK PvcKoduKAPAK PvcKoduKAPAK))(setq doorFlags::p2cFrameThick 55))
(defun ADINISENKOY_SETS()(setq doorFlags::p2cDoorSource "INSOURCE")(setq doorFlags::p2cEdges (list PvcKoduKAPAK PvcKoduKAPAK PvcKoduKAPAK PvcKoduKAPAK))(setq doorFlags::p2cFrameThick 55))  
(defun DIMHOR_SETS()(setq doorFlags::p2cDoorSource "INSOURCE")(setq doorFlags::p2cEdges (list PvcKoduKAPAK PvcKoduKAPAK PvcKoduKAPAK PvcKoduKAPAK))(setq doorFlags::p2cFrameThick 55))       
(defun DUZDIK_SETS()(setq doorFlags::p2cDoorSource "INSOURCE")(setq doorFlags::p2cEdges (list PvcKoduKAPAK PvcKoduKAPAK PvcKoduKAPAK PvcKoduKAPAK))(setq doorFlags::p2cFrameThick 55))       
(defun CERCEVE_SETS()(setq doorFlags::p2cDoorSource "INSOURCE")(setq doorFlags::p2cEdges (list PvcKoduKAPAK PvcKoduKAPAK PvcKoduKAPAK PvcKoduKAPAK))(setq doorFlags::p2cFrameThick 55))      
(defun KK001_SETS()(setq doorFlags::p2cDoorSource "INSOURCE")(setq doorFlags::p2cEdges (list PvcKoduKAPAK PvcKoduKAPAK PvcKoduKAPAK PvcKoduKAPAK))(setq doorFlags::p2cFrameThick 55))        
(defun KK002_SETS()(setq doorFlags::p2cDoorSource "INSOURCE")(setq doorFlags::p2cEdges (list PvcKoduKAPAK PvcKoduKAPAK PvcKoduKAPAK PvcKoduKAPAK))(setq doorFlags::p2cFrameThick 55))        
(defun KK003_SETS()(setq doorFlags::p2cDoorSource "INSOURCE")(setq doorFlags::p2cEdges (list PvcKoduKAPAK PvcKoduKAPAK PvcKoduKAPAK PvcKoduKAPAK))(setq doorFlags::p2cFrameThick 55))        
(defun KK004_SETS()(setq doorFlags::p2cDoorSource "INSOURCE")(setq doorFlags::p2cEdges (list PvcKoduKAPAK PvcKoduKAPAK PvcKoduKAPAK PvcKoduKAPAK))(setq doorFlags::p2cFrameThick 55))        
(defun PANJUR_SETS()(setq doorFlags::p2cDoorSource "INSOURCE")(setq doorFlags::p2cEdges (list PvcKoduKAPAK PvcKoduKAPAK PvcKoduKAPAK PvcKoduKAPAK))(setq doorFlags::p2cFrameThick 55))       
(defun GOBEKLI_SETS()(setq doorFlags::p2cDoorSource "INSOURCE")(setq doorFlags::p2cEdges (list PvcKoduKAPAK PvcKoduKAPAK PvcKoduKAPAK PvcKoduKAPAK))(setq doorFlags::p2cFrameThick 55))      
(defun GOKER_SETS()(setq doorFlags::p2cDoorSource "INSOURCE")(setq doorFlags::p2cEdges (list PvcKoduKAPAK PvcKoduKAPAK PvcKoduKAPAK PvcKoduKAPAK))(setq doorFlags::p2cFrameThick 55))        
(defun KEMER_SETS()(setq doorFlags::p2cDoorSource "INSOURCE")(setq doorFlags::p2cEdges (list PvcKoduKAPAK PvcKoduKAPAK PvcKoduKAPAK PvcKoduKAPAK))(setq doorFlags::p2cFrameThick 55))        
(defun KLASIK1_SETS()(setq doorFlags::p2cDoorSource "INSOURCE")(setq doorFlags::p2cEdges (list PvcKoduKAPAK PvcKoduKAPAK PvcKoduKAPAK PvcKoduKAPAK))(setq doorFlags::p2cFrameThick 55))      
(defun KLASIK2_SETS()(setq doorFlags::p2cDoorSource "INSOURCE")(setq doorFlags::p2cEdges (list PvcKoduKAPAK PvcKoduKAPAK PvcKoduKAPAK PvcKoduKAPAK))(setq doorFlags::p2cFrameThick 55))      
(defun KLASIK3_SETS()(setq doorFlags::p2cDoorSource "INSOURCE")(setq doorFlags::p2cEdges (list PvcKoduKAPAK PvcKoduKAPAK PvcKoduKAPAK PvcKoduKAPAK))(setq doorFlags::p2cFrameThick 55))      
(defun KLASIK4_SETS()(setq doorFlags::p2cDoorSource "INSOURCE")(setq doorFlags::p2cEdges (list PvcKoduKAPAK PvcKoduKAPAK PvcKoduKAPAK PvcKoduKAPAK))(setq doorFlags::p2cFrameThick 55))      
(defun KLS5_SETS()(setq doorFlags::p2cDoorSource "INSOURCE")(setq doorFlags::p2cEdges (list PvcKoduKAPAK PvcKoduKAPAK PvcKoduKAPAK PvcKoduKAPAK))(setq doorFlags::p2cFrameThick 55))         
(defun RUSTIK1_SETS()(setq doorFlags::p2cDoorSource "INSOURCE")(setq doorFlags::p2cEdges (list PvcKoduKAPAK PvcKoduKAPAK PvcKoduKAPAK PvcKoduKAPAK))(setq doorFlags::p2cFrameThick 55))      
(defun RUSTIK2_SETS()(setq doorFlags::p2cDoorSource "INSOURCE")(setq doorFlags::p2cEdges (list PvcKoduKAPAK PvcKoduKAPAK PvcKoduKAPAK PvcKoduKAPAK))(setq doorFlags::p2cFrameThick 55))      
(defun ANTIC_SETS()(setq doorFlags::p2cDoorSource "INSOURCE")(setq doorFlags::p2cEdges (list PvcKoduKAPAK PvcKoduKAPAK PvcKoduKAPAK PvcKoduKAPAK))(setq doorFlags::p2cFrameThick 55))        
(defun Ahsap_SETS()(setq doorFlags::p2cDoorSource "INSOURCE")(setq doorFlags::p2cEdges (list PvcKoduKAPAK PvcKoduKAPAK PvcKoduKAPAK PvcKoduKAPAK))(setq doorFlags::p2cFrameThick 55))        
(defun KLSFUG_SETS()(setq doorFlags::p2cDoorSource "INSOURCE")(setq doorFlags::p2cEdges (list PvcKoduKAPAK PvcKoduKAPAK PvcKoduKAPAK PvcKoduKAPAK))(setq doorFlags::p2cFrameThick 55))       
(defun PARKUT_SETS()(setq doorFlags::p2cDoorSource "INSOURCE")(setq doorFlags::p2cEdges (list PvcKoduKAPAK PvcKoduKAPAK PvcKoduKAPAK PvcKoduKAPAK))(setq doorFlags::p2cFrameThick 55))       
(defun KLS07_SETS()(setq doorFlags::p2cDoorSource "INSOURCE")(setq doorFlags::p2cEdges (list PvcKoduKAPAK PvcKoduKAPAK PvcKoduKAPAK PvcKoduKAPAK))(setq doorFlags::p2cFrameThick 55))        
(defun KLS08_SETS()(setq doorFlags::p2cDoorSource "INSOURCE")(setq doorFlags::p2cEdges (list PvcKoduKAPAK PvcKoduKAPAK PvcKoduKAPAK PvcKoduKAPAK))(setq doorFlags::p2cFrameThick 55))        
(defun KLS09_SETS()(setq doorFlags::p2cDoorSource "INSOURCE")(setq doorFlags::p2cEdges (list PvcKoduKAPAK PvcKoduKAPAK PvcKoduKAPAK PvcKoduKAPAK))(setq doorFlags::p2cFrameThick 55))        
(defun KLAS_SETS()(setq doorFlags::p2cDoorSource "INSOURCE")(setq doorFlags::p2cEdges (list PvcKoduKAPAK PvcKoduKAPAK PvcKoduKAPAK PvcKoduKAPAK))(setq doorFlags::p2cFrameThick 55))         
(defun COUNTRY_SETS()(setq doorFlags::p2cDoorSource "INSOURCE")(setq doorFlags::p2cEdges (list PvcKoduKAPAK PvcKoduKAPAK PvcKoduKAPAK PvcKoduKAPAK))(setq doorFlags::p2cFrameThick 55))      
(defun KLASIK10_SETS()(setq doorFlags::p2cDoorSource "INSOURCE")(setq doorFlags::p2cEdges (list PvcKoduKAPAK PvcKoduKAPAK PvcKoduKAPAK PvcKoduKAPAK))(setq doorFlags::p2cFrameThick 55))     
(defun DIKCIZGILI_SETS()(setq doorFlags::p2cDoorSource "INSOURCE")(setq doorFlags::p2cEdges (list PvcKoduKAPAK PvcKoduKAPAK PvcKoduKAPAK PvcKoduKAPAK))(setq doorFlags::p2cFrameThick 55))   
(defun FONTE_SETS()(setq doorFlags::p2cDoorSource "INSOURCE")(setq doorFlags::p2cEdges (list PvcKoduKAPAK PvcKoduKAPAK PvcKoduKAPAK PvcKoduKAPAK))(setq doorFlags::p2cFrameThick 55))        
(defun DEKAPE_SETS()(setq doorFlags::p2cDoorSource "INSOURCE")(setq doorFlags::p2cEdges (list PvcKoduKAPAK PvcKoduKAPAK PvcKoduKAPAK PvcKoduKAPAK))(setq doorFlags::p2cFrameThick 55))       
(defun SIMENA_SETS()(setq doorFlags::p2cDoorSource "INSOURCE")(setq doorFlags::p2cEdges (list PvcKoduKAPAK PvcKoduKAPAK PvcKoduKAPAK PvcKoduKAPAK))(setq doorFlags::p2cFrameThick 55))       
(defun NICEA_SETS()(setq doorFlags::p2cDoorSource "INSOURCE")(setq doorFlags::p2cEdges (list PvcKoduKAPAK PvcKoduKAPAK PvcKoduKAPAK PvcKoduKAPAK))(setq doorFlags::p2cFrameThick 55))        
(defun ARNES_SETS()(setq doorFlags::p2cDoorSource "INSOURCE")(setq doorFlags::p2cEdges (list PvcKoduKAPAK PvcKoduKAPAK PvcKoduKAPAK PvcKoduKAPAK))(setq doorFlags::p2cFrameThick 55))        
(defun RENATA_SETS()(setq doorFlags::p2cDoorSource "INSOURCE")(setq doorFlags::p2cEdges (list PvcKoduKAPAK PvcKoduKAPAK PvcKoduKAPAK PvcKoduKAPAK))(setq doorFlags::p2cFrameThick 55))       
(defun ADDEKAPE_SETS()(setq doorFlags::p2cDoorSource "INSOURCE")(setq doorFlags::p2cEdges (list PvcKoduKAPAK PvcKoduKAPAK PvcKoduKAPAK PvcKoduKAPAK))(setq doorFlags::p2cFrameThick 55))     
(defun ADSIMENA_SETS()(setq doorFlags::p2cDoorSource "INSOURCE")(setq doorFlags::p2cEdges (list PvcKoduKAPAK PvcKoduKAPAK PvcKoduKAPAK PvcKoduKAPAK))(setq doorFlags::p2cFrameThick 55))     
(defun ADNICEA_SETS()(setq doorFlags::p2cDoorSource "INSOURCE")(setq doorFlags::p2cEdges (list PvcKoduKAPAK PvcKoduKAPAK PvcKoduKAPAK PvcKoduKAPAK))(setq doorFlags::p2cFrameThick 55))      
(defun ADARNES_SETS()(setq doorFlags::p2cDoorSource "INSOURCE")(setq doorFlags::p2cEdges (list PvcKoduKAPAK PvcKoduKAPAK PvcKoduKAPAK PvcKoduKAPAK))(setq doorFlags::p2cFrameThick 55))      
(defun ADRENATA_SETS()(setq doorFlags::p2cDoorSource "INSOURCE")(setq doorFlags::p2cEdges (list PvcKoduKAPAK PvcKoduKAPAK PvcKoduKAPAK PvcKoduKAPAK))(setq doorFlags::p2cFrameThick 55))     
(defun YTCZ_SETS()(setq doorFlags::p2cDoorSource "INSOURCE")(setq doorFlags::p2cEdges (list PvcKoduKAPAK PvcKoduKAPAK PvcKoduKAPAK PvcKoduKAPAK))(setq doorFlags::p2cFrameThick 55))         
(defun CIZGILI_SETS()(setq doorFlags::p2cDoorSource "INSOURCE")(setq doorFlags::p2cEdges (list PvcKoduKAPAK PvcKoduKAPAK PvcKoduKAPAK PvcKoduKAPAK))(setq doorFlags::p2cFrameThick 55))      
(defun KEMERDC_SETS()(setq doorFlags::p2cDoorSource "INSOURCE")(setq doorFlags::p2cEdges (list PvcKoduKAPAK PvcKoduKAPAK PvcKoduKAPAK PvcKoduKAPAK))(setq doorFlags::p2cFrameThick 55))      
(defun KLSMEMBRAN1_SETS()(setq doorFlags::p2cDoorSource "INSOURCE")(setq doorFlags::p2cEdges (list PvcKoduKAPAK PvcKoduKAPAK PvcKoduKAPAK PvcKoduKAPAK))(setq doorFlags::p2cFrameThick 55))  
(defun KLSMEMBRAN2_SETS()(setq doorFlags::p2cDoorSource "INSOURCE")(setq doorFlags::p2cEdges (list PvcKoduKAPAK PvcKoduKAPAK PvcKoduKAPAK PvcKoduKAPAK))(setq doorFlags::p2cFrameThick 55))  
(defun KLSMEMBRAN3_SETS()(setq doorFlags::p2cDoorSource "INSOURCE")(setq doorFlags::p2cEdges (list PvcKoduKAPAK PvcKoduKAPAK PvcKoduKAPAK PvcKoduKAPAK))(setq doorFlags::p2cFrameThick 55))  
(defun SARP_SETS()(setq doorFlags::p2cDoorSource "INSOURCE")(setq doorFlags::p2cEdges (list PvcKoduKAPAK PvcKoduKAPAK PvcKoduKAPAK PvcKoduKAPAK))(setq doorFlags::p2cFrameThick 55))         
(defun KAPAK100_SETS()(setq doorFlags::p2cDoorSource "INSOURCE")(setq doorFlags::p2cEdges (list PvcKoduKAPAK PvcKoduKAPAK PvcKoduKAPAK PvcKoduKAPAK))(setq doorFlags::p2cFrameThick 55))     
(defun KAPAK101_SETS()(setq doorFlags::p2cDoorSource "INSOURCE")(setq doorFlags::p2cEdges (list PvcKoduKAPAK PvcKoduKAPAK PvcKoduKAPAK PvcKoduKAPAK))(setq doorFlags::p2cFrameThick 55))     
(defun KAPAK102_SETS()(setq doorFlags::p2cDoorSource "INSOURCE")(setq doorFlags::p2cEdges (list PvcKoduKAPAK PvcKoduKAPAK PvcKoduKAPAK PvcKoduKAPAK))(setq doorFlags::p2cFrameThick 55))
(defun KAPAK103_SETS()(setq doorFlags::p2cDoorSource "INSOURCE")(setq doorFlags::p2cEdges (list PvcKoduKAPAK PvcKoduKAPAK PvcKoduKAPAK PvcKoduKAPAK))(setq doorFlags::p2cFrameThick 55))     
(defun KAPAK104_SETS()(setq doorFlags::p2cDoorSource "INSOURCE")(setq doorFlags::p2cEdges (list PvcKoduKAPAK PvcKoduKAPAK PvcKoduKAPAK PvcKoduKAPAK))(setq doorFlags::p2cFrameThick 55))     
(defun KAPAK105_SETS()(setq doorFlags::p2cDoorSource "INSOURCE")(setq doorFlags::p2cEdges (list PvcKoduKAPAK PvcKoduKAPAK PvcKoduKAPAK PvcKoduKAPAK))(setq doorFlags::p2cFrameThick 55))     
(defun KAPAK106_SETS()(setq doorFlags::p2cDoorSource "INSOURCE")(setq doorFlags::p2cEdges (list PvcKoduKAPAK PvcKoduKAPAK PvcKoduKAPAK PvcKoduKAPAK))(setq doorFlags::p2cFrameThick 55))     
(defun KARYA_SETS()(setq doorFlags::p2cDoorSource "INSOURCE")(setq doorFlags::p2cEdges (list PvcKoduKAPAK PvcKoduKAPAK PvcKoduKAPAK PvcKoduKAPAK))(setq doorFlags::p2cFrameThick 55))        
(defun ELIF_SETS()(setq doorFlags::p2cDoorSource "INSOURCE")(setq doorFlags::p2cEdges (list PvcKoduKAPAK PvcKoduKAPAK PvcKoduKAPAK PvcKoduKAPAK))(setq doorFlags::p2cFrameThick 55))         
(defun SENA_SETS()(setq doorFlags::p2cDoorSource "INSOURCE")(setq doorFlags::p2cEdges (list PvcKoduKAPAK PvcKoduKAPAK PvcKoduKAPAK PvcKoduKAPAK))(setq doorFlags::p2cFrameThick 55))         
(defun SUEDA_SETS()(setq doorFlags::p2cDoorSource "INSOURCE")(setq doorFlags::p2cEdges (list PvcKoduKAPAK PvcKoduKAPAK PvcKoduKAPAK PvcKoduKAPAK))(setq doorFlags::p2cFrameThick 55))        
(defun AVANGART_SETS()(setq doorFlags::p2cDoorSource "INSOURCE")(setq doorFlags::p2cEdges (list PvcKoduKAPAK PvcKoduKAPAK PvcKoduKAPAK PvcKoduKAPAK))(setq doorFlags::p2cFrameThick 55))     
(defun GOKKER_SETS()(setq doorFlags::p2cDoorSource "INSOURCE")(setq doorFlags::p2cEdges (list PvcKoduKAPAK PvcKoduKAPAK PvcKoduKAPAK PvcKoduKAPAK))(setq doorFlags::p2cFrameThick 55))       
(defun ORCUNN_SETS()(setq doorFlags::p2cDoorSource "INSOURCE")(setq doorFlags::p2cEdges (list PvcKoduKAPAK PvcKoduKAPAK PvcKoduKAPAK PvcKoduKAPAK))(setq doorFlags::p2cFrameThick 55))       
(defun XKAPAK_SETS()(setq doorFlags::p2cDoorSource "INSOURCE")(setq doorFlags::p2cEdges (list PvcKoduKAPAK PvcKoduKAPAK PvcKoduKAPAK PvcKoduKAPAK))(setq doorFlags::p2cFrameThick 55))       
(defun BAKLAVA_SETS()(setq doorFlags::p2cDoorSource "INSOURCE")(setq doorFlags::p2cEdges (list PvcKoduKAPAK PvcKoduKAPAK PvcKoduKAPAK PvcKoduKAPAK))(setq doorFlags::p2cFrameThick 55))      
(defun CAMBAKLAVA_SETS()(setq doorFlags::p2cDoorSource "INSOURCE")(setq doorFlags::p2cEdges (list PvcKoduKAPAK PvcKoduKAPAK PvcKoduKAPAK PvcKoduKAPAK))(setq doorFlags::p2cFrameThick 55))   
(defun BUXXKAPAK_SETS()(setq doorFlags::p2cDoorSource "INSOURCE")(setq doorFlags::p2cEdges (list PvcKoduKAPAK PvcKoduKAPAK PvcKoduKAPAK PvcKoduKAPAK))(setq doorFlags::p2cFrameThick 55))    
(defun INCEFUGALI_SETS()(setq doorFlags::p2cDoorSource "INSOURCE")(setq doorFlags::p2cEdges (list PvcKoduKAPAK PvcKoduKAPAK PvcKoduKAPAK PvcKoduKAPAK))(setq doorFlags::p2cFrameThick 55))   
(defun MEMBRAN1_SETS()(setq doorFlags::p2cDoorSource "INSOURCE")(setq doorFlags::p2cEdges (list PvcKoduKAPAK PvcKoduKAPAK PvcKoduKAPAK PvcKoduKAPAK))(setq doorFlags::p2cFrameThick 55))      
(defun MEMBRAN2_SETS()(setq doorFlags::p2cDoorSource "INSOURCE")(setq doorFlags::p2cEdges (list PvcKoduKAPAK PvcKoduKAPAK PvcKoduKAPAK PvcKoduKAPAK))(setq doorFlags::p2cFrameThick 55))      
(defun MEMBRAN5_SETS()(setq doorFlags::p2cDoorSource "INSOURCE")(setq doorFlags::p2cEdges (list PvcKoduKAPAK PvcKoduKAPAK PvcKoduKAPAK PvcKoduKAPAK))(setq doorFlags::p2cFrameThick 55))      
(defun PAHYUZ_SETS()(setq doorFlags::p2cDoorSource "INSOURCE")(setq doorFlags::p2cEdges (list PvcKoduKAPAK PvcKoduKAPAK PvcKoduKAPAK PvcKoduKAPAK))(setq doorFlags::p2cFrameThick 55))        
(defun FUGA1_SETS()(setq doorFlags::p2cDoorSource "INSOURCE")(setq doorFlags::p2cEdges (list PvcKoduKAPAK PvcKoduKAPAK PvcKoduKAPAK PvcKoduKAPAK))(setq doorFlags::p2cFrameThick 55))         
(defun FUGA2_SETS()(setq doorFlags::p2cDoorSource "INSOURCE")(setq doorFlags::p2cEdges (list PvcKoduKAPAK PvcKoduKAPAK PvcKoduKAPAK PvcKoduKAPAK))(setq doorFlags::p2cFrameThick 55))         
(defun PAHFUGA_SETS()(setq doorFlags::p2cDoorSource "INSOURCE")(setq doorFlags::p2cEdges (list PvcKoduKAPAK PvcKoduKAPAK PvcKoduKAPAK PvcKoduKAPAK))(setq doorFlags::p2cFrameThick 55))       
(defun SDERZ_SETS()(setq doorFlags::p2cDoorSource "INSOURCE")(setq doorFlags::p2cEdges (list PvcKoduKAPAK PvcKoduKAPAK PvcKoduKAPAK PvcKoduKAPAK))(setq doorFlags::p2cFrameThick 55))         
(defun SERIT_SETS()(setq doorFlags::p2cDoorSource "INSOURCE")(setq doorFlags::p2cEdges (list PvcKoduKAPAK PvcKoduKAPAK PvcKoduKAPAK PvcKoduKAPAK))(setq doorFlags::p2cFrameThick 55))         
(defun KEMERDIS_SETS()(setq doorFlags::p2cDoorSource "INSOURCE")(setq doorFlags::p2cEdges (list PvcKoduKAPAK PvcKoduKAPAK PvcKoduKAPAK PvcKoduKAPAK))(setq doorFlags::p2cFrameThick 55))      
(defun YSERIT_SETS()(setq doorFlags::p2cDoorSource "INSOURCE")(setq doorFlags::p2cEdges (list PvcKoduKAPAK PvcKoduKAPAK PvcKoduKAPAK PvcKoduKAPAK))(setq doorFlags::p2cFrameThick 55))        
(defun 4DERZ_SETS()(setq doorFlags::p2cDoorSource "INSOURCE")(setq doorFlags::p2cEdges (list PvcKoduKAPAK PvcKoduKAPAK PvcKoduKAPAK PvcKoduKAPAK))(setq doorFlags::p2cFrameThick 55))         
(defun SIDE_SETS()(setq doorFlags::p2cDoorSource "INSOURCE")(setq doorFlags::p2cEdges (list PvcKoduKAPAK PvcKoduKAPAK PvcKoduKAPAK PvcKoduKAPAK))(setq doorFlags::p2cFrameThick 55))          
(defun YTCZ_SETS()(setq doorFlags::p2cDoorSource "INSOURCE")(setq doorFlags::p2cEdges (list PvcKoduKAPAK PvcKoduKAPAK PvcKoduKAPAK PvcKoduKAPAK))(setq doorFlags::p2cFrameThick 55))          
(defun B102_SETS()(setq doorFlags::p2cDoorSource "INSOURCE")(setq doorFlags::p2cEdges (list PvcKoduKAPAK PvcKoduKAPAK PvcKoduKAPAK PvcKoduKAPAK))(setq doorFlags::p2cFrameThick 55))          
(defun B104_SETS()(setq doorFlags::p2cDoorSource "INSOURCE")(setq doorFlags::p2cEdges (list PvcKoduKAPAK PvcKoduKAPAK PvcKoduKAPAK PvcKoduKAPAK))(setq doorFlags::p2cFrameThick 55))          
(defun B105_SETS()(setq doorFlags::p2cDoorSource "INSOURCE")(setq doorFlags::p2cEdges (list PvcKoduKAPAK PvcKoduKAPAK PvcKoduKAPAK PvcKoduKAPAK))(setq doorFlags::p2cFrameThick 55))          
(defun B106_SETS()(setq doorFlags::p2cDoorSource "INSOURCE")(setq doorFlags::p2cEdges (list PvcKoduKAPAK PvcKoduKAPAK PvcKoduKAPAK PvcKoduKAPAK))(setq doorFlags::p2cFrameThick 55))          
(defun B112_SETS()(setq doorFlags::p2cDoorSource "INSOURCE")(setq doorFlags::p2cEdges (list PvcKoduKAPAK PvcKoduKAPAK PvcKoduKAPAK PvcKoduKAPAK))(setq doorFlags::p2cFrameThick 55))          
(defun B121_SETS()(setq doorFlags::p2cDoorSource "INSOURCE")(setq doorFlags::p2cEdges (list PvcKoduKAPAK PvcKoduKAPAK PvcKoduKAPAK PvcKoduKAPAK))(setq doorFlags::p2cFrameThick 55))          
(defun B130_SETS()(setq doorFlags::p2cDoorSource "INSOURCE")(setq doorFlags::p2cEdges (list PvcKoduKAPAK PvcKoduKAPAK PvcKoduKAPAK PvcKoduKAPAK))(setq doorFlags::p2cFrameThick 55))          
(defun B137_SETS()(setq doorFlags::p2cDoorSource "INSOURCE")(setq doorFlags::p2cEdges (list PvcKoduKAPAK PvcKoduKAPAK PvcKoduKAPAK PvcKoduKAPAK))(setq doorFlags::p2cFrameThick 55))          
(defun B147_SETS()(setq doorFlags::p2cDoorSource "INSOURCE")(setq doorFlags::p2cEdges (list PvcKoduKAPAK PvcKoduKAPAK PvcKoduKAPAK PvcKoduKAPAK))(setq doorFlags::p2cFrameThick 55))          
(defun B150_SETS()(setq doorFlags::p2cDoorSource "INSOURCE")(setq doorFlags::p2cEdges (list PvcKoduKAPAK PvcKoduKAPAK PvcKoduKAPAK PvcKoduKAPAK))(setq doorFlags::p2cFrameThick 55))          
(defun B151_SETS()(setq doorFlags::p2cDoorSource "INSOURCE")(setq doorFlags::p2cEdges (list PvcKoduKAPAK PvcKoduKAPAK PvcKoduKAPAK PvcKoduKAPAK))(setq doorFlags::p2cFrameThick 55))          
(defun B155_SETS()(setq doorFlags::p2cDoorSource "INSOURCE")(setq doorFlags::p2cEdges (list PvcKoduKAPAK PvcKoduKAPAK PvcKoduKAPAK PvcKoduKAPAK))(setq doorFlags::p2cFrameThick 55))          
(defun B157_SETS()(setq doorFlags::p2cDoorSource "INSOURCE")(setq doorFlags::p2cEdges (list PvcKoduKAPAK PvcKoduKAPAK PvcKoduKAPAK PvcKoduKAPAK))(setq doorFlags::p2cFrameThick 55))          
(defun K01DIK_SETS()(setq doorFlags::p2cDoorSource "INSOURCE")(setq doorFlags::p2cEdges (list PvcKoduKAPAK PvcKoduKAPAK PvcKoduKAPAK PvcKoduKAPAK))(setq doorFlags::p2cFrameThick 55))        
(defun K01YTY_SETS()(setq doorFlags::p2cDoorSource "INSOURCE")(setq doorFlags::p2cEdges (list PvcKoduKAPAK PvcKoduKAPAK PvcKoduKAPAK PvcKoduKAPAK))(setq doorFlags::p2cFrameThick 55))        
(defun K02DIK_SETS()(setq doorFlags::p2cDoorSource "INSOURCE")(setq doorFlags::p2cEdges (list PvcKoduKAPAK PvcKoduKAPAK PvcKoduKAPAK PvcKoduKAPAK))(setq doorFlags::p2cFrameThick 55))        
(defun K02YTY_SETS()(setq doorFlags::p2cDoorSource "INSOURCE")(setq doorFlags::p2cEdges (list PvcKoduKAPAK PvcKoduKAPAK PvcKoduKAPAK PvcKoduKAPAK))(setq doorFlags::p2cFrameThick 55))        
(defun K03DIK_SETS()(setq doorFlags::p2cDoorSource "INSOURCE")(setq doorFlags::p2cEdges (list PvcKoduKAPAK PvcKoduKAPAK PvcKoduKAPAK PvcKoduKAPAK))(setq doorFlags::p2cFrameThick 55))        
(defun K03YTY_SETS()(setq doorFlags::p2cDoorSource "INSOURCE")(setq doorFlags::p2cEdges (list PvcKoduKAPAK PvcKoduKAPAK PvcKoduKAPAK PvcKoduKAPAK))(setq doorFlags::p2cFrameThick 55))        
(defun K04DIK_SETS()(setq doorFlags::p2cDoorSource "INSOURCE")(setq doorFlags::p2cEdges (list PvcKoduKAPAK PvcKoduKAPAK PvcKoduKAPAK PvcKoduKAPAK))(setq doorFlags::p2cFrameThick 55))        
(defun K04YTY_SETS()(setq doorFlags::p2cDoorSource "INSOURCE")(setq doorFlags::p2cEdges (list PvcKoduKAPAK PvcKoduKAPAK PvcKoduKAPAK PvcKoduKAPAK))(setq doorFlags::p2cFrameThick 55))        
(defun K010DIK_SETS()(setq doorFlags::p2cDoorSource "INSOURCE")(setq doorFlags::p2cEdges (list PvcKoduKAPAK PvcKoduKAPAK PvcKoduKAPAK PvcKoduKAPAK))(setq doorFlags::p2cFrameThick 55))       
(defun K010YTY_SETS()(setq doorFlags::p2cDoorSource "INSOURCE")(setq doorFlags::p2cEdges (list PvcKoduKAPAK PvcKoduKAPAK PvcKoduKAPAK PvcKoduKAPAK))(setq doorFlags::p2cFrameThick 55))       
(defun PRAMIT_SETS()(setq doorFlags::p2cDoorSource "INSOURCE")(setq doorFlags::p2cEdges (list PvcKoduKAPAK PvcKoduKAPAK PvcKoduKAPAK PvcKoduKAPAK))(setq doorFlags::p2cFrameThick 55))        
(defun PRAMIT2_SETS()(setq doorFlags::p2cDoorSource "INSOURCE")(setq doorFlags::p2cEdges (list PvcKoduKAPAK PvcKoduKAPAK PvcKoduKAPAK PvcKoduKAPAK))(setq doorFlags::p2cFrameThick 55))       
(defun CTL66X_SETS()(setq doorFlags::p2cDoorSource "INSOURCE")(setq doorFlags::p2cEdges (list PvcKoduKAPAK PvcKoduKAPAK PvcKoduKAPAK PvcKoduKAPAK))(setq doorFlags::p2cFrameThick 55))        
(defun CTL95_SETS()(setq doorFlags::p2cDoorSource "INSOURCE")(setq doorFlags::p2cEdges (list PvcKoduKAPAK PvcKoduKAPAK PvcKoduKAPAK PvcKoduKAPAK))(setq doorFlags::p2cFrameThick 55))         
(defun CTLJAL_SETS()(setq doorFlags::p2cDoorSource "INSOURCE")(setq doorFlags::p2cEdges (list PvcKoduKAPAK PvcKoduKAPAK PvcKoduKAPAK PvcKoduKAPAK))(setq doorFlags::p2cFrameThick 55))        
(defun RDUZ_SETS()(setq doorFlags::p2cDoorSource "INSOURCE")(setq doorFlags::p2cEdges (list PvcKoduKAPAK PvcKoduKAPAK PvcKoduKAPAK PvcKoduKAPAK))(setq doorFlags::p2cFrameThick 55))          
(defun SM100_SETS()(setq doorFlags::p2cDoorSource "INSOURCE")(setq doorFlags::p2cEdges (list PvcKoduKAPAK PvcKoduKAPAK PvcKoduKAPAK PvcKoduKAPAK))(setq doorFlags::p2cFrameThick 55))         
(defun SM101_SETS()(setq doorFlags::p2cDoorSource "INSOURCE")(setq doorFlags::p2cEdges (list PvcKoduKAPAK PvcKoduKAPAK PvcKoduKAPAK PvcKoduKAPAK))(setq doorFlags::p2cFrameThick 55))         
(defun SM102_SETS()(setq doorFlags::p2cDoorSource "INSOURCE")(setq doorFlags::p2cEdges (list PvcKoduKAPAK PvcKoduKAPAK PvcKoduKAPAK PvcKoduKAPAK))(setq doorFlags::p2cFrameThick 55))         
(defun SM103_SETS()(setq doorFlags::p2cDoorSource "INSOURCE")(setq doorFlags::p2cEdges (list PvcKoduKAPAK PvcKoduKAPAK PvcKoduKAPAK PvcKoduKAPAK))(setq doorFlags::p2cFrameThick 55))         
(defun SM105_SETS()(setq doorFlags::p2cDoorSource "INSOURCE")(setq doorFlags::p2cEdges (list PvcKoduKAPAK PvcKoduKAPAK PvcKoduKAPAK PvcKoduKAPAK))(setq doorFlags::p2cFrameThick 55))         
(defun SM107_SETS()(setq doorFlags::p2cDoorSource "INSOURCE")(setq doorFlags::p2cEdges (list PvcKoduKAPAK PvcKoduKAPAK PvcKoduKAPAK PvcKoduKAPAK))(setq doorFlags::p2cFrameThick 55))         
(defun SM108_SETS()(setq doorFlags::p2cDoorSource "INSOURCE")(setq doorFlags::p2cEdges (list PvcKoduKAPAK PvcKoduKAPAK PvcKoduKAPAK PvcKoduKAPAK))(setq doorFlags::p2cFrameThick 55))         
(defun SM109_SETS()(setq doorFlags::p2cDoorSource "INSOURCE")(setq doorFlags::p2cEdges (list PvcKoduKAPAK PvcKoduKAPAK PvcKoduKAPAK PvcKoduKAPAK))(setq doorFlags::p2cFrameThick 55))         
(defun SM110_SETS()(setq doorFlags::p2cDoorSource "INSOURCE")(setq doorFlags::p2cEdges (list PvcKoduKAPAK PvcKoduKAPAK PvcKoduKAPAK PvcKoduKAPAK))(setq doorFlags::p2cFrameThick 55))         
(defun SM113_SETS()(setq doorFlags::p2cDoorSource "INSOURCE")(setq doorFlags::p2cEdges (list PvcKoduKAPAK PvcKoduKAPAK PvcKoduKAPAK PvcKoduKAPAK))(setq doorFlags::p2cFrameThick 55))         
(defun SM111_SETS()(setq doorFlags::p2cDoorSource "INSOURCE")(setq doorFlags::p2cEdges (list PvcKoduKAPAK PvcKoduKAPAK PvcKoduKAPAK PvcKoduKAPAK))(setq doorFlags::p2cFrameThick 55))         
(defun SM112_SETS()(setq doorFlags::p2cDoorSource "INSOURCE")(setq doorFlags::p2cEdges (list PvcKoduKAPAK PvcKoduKAPAK PvcKoduKAPAK PvcKoduKAPAK))(setq doorFlags::p2cFrameThick 55))         
(defun SM116_SETS()(setq doorFlags::p2cDoorSource "INSOURCE")(setq doorFlags::p2cEdges (list PvcKoduKAPAK PvcKoduKAPAK PvcKoduKAPAK PvcKoduKAPAK))(setq doorFlags::p2cFrameThick 55))         
(defun SM118_SETS()(setq doorFlags::p2cDoorSource "INSOURCE")(setq doorFlags::p2cEdges (list PvcKoduKAPAK PvcKoduKAPAK PvcKoduKAPAK PvcKoduKAPAK))(setq doorFlags::p2cFrameThick 55))         
(defun SM119_SETS()(setq doorFlags::p2cDoorSource "INSOURCE")(setq doorFlags::p2cEdges (list PvcKoduKAPAK PvcKoduKAPAK PvcKoduKAPAK PvcKoduKAPAK))(setq doorFlags::p2cFrameThick 55))         
(defun SM120_SETS()(setq doorFlags::p2cDoorSource "INSOURCE")(setq doorFlags::p2cEdges (list PvcKoduKAPAK PvcKoduKAPAK PvcKoduKAPAK PvcKoduKAPAK))(setq doorFlags::p2cFrameThick 55))         
(defun SM121_SETS()(setq doorFlags::p2cDoorSource "INSOURCE")(setq doorFlags::p2cEdges (list PvcKoduKAPAK PvcKoduKAPAK PvcKoduKAPAK PvcKoduKAPAK))(setq doorFlags::p2cFrameThick 55))         
(defun SM122_SETS()(setq doorFlags::p2cDoorSource "INSOURCE")(setq doorFlags::p2cEdges (list PvcKoduKAPAK PvcKoduKAPAK PvcKoduKAPAK PvcKoduKAPAK))(setq doorFlags::p2cFrameThick 55))         
(defun SM123_SETS()(setq doorFlags::p2cDoorSource "INSOURCE")(setq doorFlags::p2cEdges (list PvcKoduKAPAK PvcKoduKAPAK PvcKoduKAPAK PvcKoduKAPAK))(setq doorFlags::p2cFrameThick 55))         
(defun SM124_SETS()(setq doorFlags::p2cDoorSource "INSOURCE")(setq doorFlags::p2cEdges (list PvcKoduKAPAK PvcKoduKAPAK PvcKoduKAPAK PvcKoduKAPAK))(setq doorFlags::p2cFrameThick 55))         
(defun SM125_SETS()(setq doorFlags::p2cDoorSource "INSOURCE")(setq doorFlags::p2cEdges (list PvcKoduKAPAK PvcKoduKAPAK PvcKoduKAPAK PvcKoduKAPAK))(setq doorFlags::p2cFrameThick 55))         
(defun SM128_SETS()(setq doorFlags::p2cDoorSource "INSOURCE")(setq doorFlags::p2cEdges (list PvcKoduKAPAK PvcKoduKAPAK PvcKoduKAPAK PvcKoduKAPAK))(setq doorFlags::p2cFrameThick 55))         
(defun SM144_SETS()(setq doorFlags::p2cDoorSource "INSOURCE")(setq doorFlags::p2cEdges (list PvcKoduKAPAK PvcKoduKAPAK PvcKoduKAPAK PvcKoduKAPAK))(setq doorFlags::p2cFrameThick 55))         
(defun SM148_SETS()(setq doorFlags::p2cDoorSource "INSOURCE")(setq doorFlags::p2cEdges (list PvcKoduKAPAK PvcKoduKAPAK PvcKoduKAPAK PvcKoduKAPAK))(setq doorFlags::p2cFrameThick 55))         
(defun SM150_SETS()(setq doorFlags::p2cDoorSource "INSOURCE")(setq doorFlags::p2cEdges (list PvcKoduKAPAK PvcKoduKAPAK PvcKoduKAPAK PvcKoduKAPAK))(setq doorFlags::p2cFrameThick 55))         
(defun SM152_SETS()(setq doorFlags::p2cDoorSource "INSOURCE")(setq doorFlags::p2cEdges (list PvcKoduKAPAK PvcKoduKAPAK PvcKoduKAPAK PvcKoduKAPAK))(setq doorFlags::p2cFrameThick 55))         
(defun SM155_SETS()(setq doorFlags::p2cDoorSource "INSOURCE")(setq doorFlags::p2cEdges (list PvcKoduKAPAK PvcKoduKAPAK PvcKoduKAPAK PvcKoduKAPAK))(setq doorFlags::p2cFrameThick 55))         
(defun SM170_SETS()(setq doorFlags::p2cDoorSource "INSOURCE")(setq doorFlags::p2cEdges (list PvcKoduKAPAK PvcKoduKAPAK PvcKoduKAPAK PvcKoduKAPAK))(setq doorFlags::p2cFrameThick 55))         
(defun SM171_SETS()(setq doorFlags::p2cDoorSource "INSOURCE")(setq doorFlags::p2cEdges (list PvcKoduKAPAK PvcKoduKAPAK PvcKoduKAPAK PvcKoduKAPAK))(setq doorFlags::p2cFrameThick 55))         
(defun SM172_SETS()(setq doorFlags::p2cDoorSource "INSOURCE")(setq doorFlags::p2cEdges (list PvcKoduKAPAK PvcKoduKAPAK PvcKoduKAPAK PvcKoduKAPAK))(setq doorFlags::p2cFrameThick 55))         
(defun SM173_SETS()(setq doorFlags::p2cDoorSource "INSOURCE")(setq doorFlags::p2cEdges (list PvcKoduKAPAK PvcKoduKAPAK PvcKoduKAPAK PvcKoduKAPAK))(setq doorFlags::p2cFrameThick 55))         
(defun SM174_SETS()(setq doorFlags::p2cDoorSource "INSOURCE")(setq doorFlags::p2cEdges (list PvcKoduKAPAK PvcKoduKAPAK PvcKoduKAPAK PvcKoduKAPAK))(setq doorFlags::p2cFrameThick 55))         
(defun SM175_SETS()(setq doorFlags::p2cDoorSource "INSOURCE")(setq doorFlags::p2cEdges (list PvcKoduKAPAK PvcKoduKAPAK PvcKoduKAPAK PvcKoduKAPAK))(setq doorFlags::p2cFrameThick 55))         
(defun SM178_SETS()(setq doorFlags::p2cDoorSource "INSOURCE")(setq doorFlags::p2cEdges (list PvcKoduKAPAK PvcKoduKAPAK PvcKoduKAPAK PvcKoduKAPAK))(setq doorFlags::p2cFrameThick 55))         
(defun SM179_SETS()(setq doorFlags::p2cDoorSource "INSOURCE")(setq doorFlags::p2cEdges (list PvcKoduKAPAK PvcKoduKAPAK PvcKoduKAPAK PvcKoduKAPAK))(setq doorFlags::p2cFrameThick 55))         
(defun SM180_SETS()(setq doorFlags::p2cDoorSource "INSOURCE")(setq doorFlags::p2cEdges (list PvcKoduKAPAK PvcKoduKAPAK PvcKoduKAPAK PvcKoduKAPAK))(setq doorFlags::p2cFrameThick 55))         
(defun SM181_SETS()(setq doorFlags::p2cDoorSource "INSOURCE")(setq doorFlags::p2cEdges (list PvcKoduKAPAK PvcKoduKAPAK PvcKoduKAPAK PvcKoduKAPAK))(setq doorFlags::p2cFrameThick 55))         
(defun SM182_SETS()(setq doorFlags::p2cDoorSource "INSOURCE")(setq doorFlags::p2cEdges (list PvcKoduKAPAK PvcKoduKAPAK PvcKoduKAPAK PvcKoduKAPAK))(setq doorFlags::p2cFrameThick 55))         
(defun SM184_SETS()(setq doorFlags::p2cDoorSource "INSOURCE")(setq doorFlags::p2cEdges (list PvcKoduKAPAK PvcKoduKAPAK PvcKoduKAPAK PvcKoduKAPAK))(setq doorFlags::p2cFrameThick 55))         
(defun SM185_SETS()(setq doorFlags::p2cDoorSource "INSOURCE")(setq doorFlags::p2cEdges (list PvcKoduKAPAK PvcKoduKAPAK PvcKoduKAPAK PvcKoduKAPAK))(setq doorFlags::p2cFrameThick 55))         
(defun SM186_SETS()(setq doorFlags::p2cDoorSource "INSOURCE")(setq doorFlags::p2cEdges (list PvcKoduKAPAK PvcKoduKAPAK PvcKoduKAPAK PvcKoduKAPAK))(setq doorFlags::p2cFrameThick 55))         
(defun SM187_SETS()(setq doorFlags::p2cDoorSource "INSOURCE")(setq doorFlags::p2cEdges (list PvcKoduKAPAK PvcKoduKAPAK PvcKoduKAPAK PvcKoduKAPAK))(setq doorFlags::p2cFrameThick 55))         
(defun SM189_SETS()(setq doorFlags::p2cDoorSource "INSOURCE")(setq doorFlags::p2cEdges (list PvcKoduKAPAK PvcKoduKAPAK PvcKoduKAPAK PvcKoduKAPAK))(setq doorFlags::p2cFrameThick 55))         
(defun SM191_SETS()(setq doorFlags::p2cDoorSource "INSOURCE")(setq doorFlags::p2cEdges (list PvcKoduKAPAK PvcKoduKAPAK PvcKoduKAPAK PvcKoduKAPAK))(setq doorFlags::p2cFrameThick 55))         
(defun SM192_SETS()(setq doorFlags::p2cDoorSource "INSOURCE")(setq doorFlags::p2cEdges (list PvcKoduKAPAK PvcKoduKAPAK PvcKoduKAPAK PvcKoduKAPAK))(setq doorFlags::p2cFrameThick 55))         
(defun SM194_SETS()(setq doorFlags::p2cDoorSource "INSOURCE")(setq doorFlags::p2cEdges (list PvcKoduKAPAK PvcKoduKAPAK PvcKoduKAPAK PvcKoduKAPAK))(setq doorFlags::p2cFrameThick 55))         
(defun SM195_SETS()(setq doorFlags::p2cDoorSource "INSOURCE")(setq doorFlags::p2cEdges (list PvcKoduKAPAK PvcKoduKAPAK PvcKoduKAPAK PvcKoduKAPAK))(setq doorFlags::p2cFrameThick 55))         
(defun SM196_SETS()(setq doorFlags::p2cDoorSource "INSOURCE")(setq doorFlags::p2cEdges (list PvcKoduKAPAK PvcKoduKAPAK PvcKoduKAPAK PvcKoduKAPAK))(setq doorFlags::p2cFrameThick 55))         
(defun SM197_SETS()(setq doorFlags::p2cDoorSource "INSOURCE")(setq doorFlags::p2cEdges (list PvcKoduKAPAK PvcKoduKAPAK PvcKoduKAPAK PvcKoduKAPAK))(setq doorFlags::p2cFrameThick 55))         
(defun SM198_SETS()(setq doorFlags::p2cDoorSource "INSOURCE")(setq doorFlags::p2cEdges (list PvcKoduKAPAK PvcKoduKAPAK PvcKoduKAPAK PvcKoduKAPAK))(setq doorFlags::p2cFrameThick 55))         
(defun SM203_SETS()(setq doorFlags::p2cDoorSource "INSOURCE")(setq doorFlags::p2cEdges (list PvcKoduKAPAK PvcKoduKAPAK PvcKoduKAPAK PvcKoduKAPAK))(setq doorFlags::p2cFrameThick 55))         
(defun SM204_SETS()(setq doorFlags::p2cDoorSource "INSOURCE")(setq doorFlags::p2cEdges (list PvcKoduKAPAK PvcKoduKAPAK PvcKoduKAPAK PvcKoduKAPAK))(setq doorFlags::p2cFrameThick 55))         
(defun SM205_SETS()(setq doorFlags::p2cDoorSource "INSOURCE")(setq doorFlags::p2cEdges (list PvcKoduKAPAK PvcKoduKAPAK PvcKoduKAPAK PvcKoduKAPAK))(setq doorFlags::p2cFrameThick 55))         
(defun SM206_SETS()(setq doorFlags::p2cDoorSource "INSOURCE")(setq doorFlags::p2cEdges (list PvcKoduKAPAK PvcKoduKAPAK PvcKoduKAPAK PvcKoduKAPAK))(setq doorFlags::p2cFrameThick 55))         
(defun SM207_SETS()(setq doorFlags::p2cDoorSource "INSOURCE")(setq doorFlags::p2cEdges (list PvcKoduKAPAK PvcKoduKAPAK PvcKoduKAPAK PvcKoduKAPAK))(setq doorFlags::p2cFrameThick 55))         
(defun SM208_SETS()(setq doorFlags::p2cDoorSource "INSOURCE")(setq doorFlags::p2cEdges (list PvcKoduKAPAK PvcKoduKAPAK PvcKoduKAPAK PvcKoduKAPAK))(setq doorFlags::p2cFrameThick 55))         
(defun SM209_SETS()(setq doorFlags::p2cDoorSource "INSOURCE")(setq doorFlags::p2cEdges (list PvcKoduKAPAK PvcKoduKAPAK PvcKoduKAPAK PvcKoduKAPAK))(setq doorFlags::p2cFrameThick 55))         
(defun SM210_SETS()(setq doorFlags::p2cDoorSource "INSOURCE")(setq doorFlags::p2cEdges (list PvcKoduKAPAK PvcKoduKAPAK PvcKoduKAPAK PvcKoduKAPAK))(setq doorFlags::p2cFrameThick 55))         
(defun SM211_SETS()(setq doorFlags::p2cDoorSource "INSOURCE")(setq doorFlags::p2cEdges (list PvcKoduKAPAK PvcKoduKAPAK PvcKoduKAPAK PvcKoduKAPAK))(setq doorFlags::p2cFrameThick 55))         
(defun SM212_SETS()(setq doorFlags::p2cDoorSource "INSOURCE")(setq doorFlags::p2cEdges (list PvcKoduKAPAK PvcKoduKAPAK PvcKoduKAPAK PvcKoduKAPAK))(setq doorFlags::p2cFrameThick 55))         
(defun SM214_SETS()(setq doorFlags::p2cDoorSource "INSOURCE")(setq doorFlags::p2cEdges (list PvcKoduKAPAK PvcKoduKAPAK PvcKoduKAPAK PvcKoduKAPAK))(setq doorFlags::p2cFrameThick 55))         
(defun SM213_SETS()(setq doorFlags::p2cDoorSource "INSOURCE")(setq doorFlags::p2cEdges (list PvcKoduKAPAK PvcKoduKAPAK PvcKoduKAPAK PvcKoduKAPAK))(setq doorFlags::p2cFrameThick 55))         
(defun SM216_SETS()(setq doorFlags::p2cDoorSource "INSOURCE")(setq doorFlags::p2cEdges (list PvcKoduKAPAK PvcKoduKAPAK PvcKoduKAPAK PvcKoduKAPAK))(setq doorFlags::p2cFrameThick 55))         
(defun SM217_SETS()(setq doorFlags::p2cDoorSource "INSOURCE")(setq doorFlags::p2cEdges (list PvcKoduKAPAK PvcKoduKAPAK PvcKoduKAPAK PvcKoduKAPAK))(setq doorFlags::p2cFrameThick 55))         
(defun SM218_SETS()(setq doorFlags::p2cDoorSource "INSOURCE")(setq doorFlags::p2cEdges (list PvcKoduKAPAK PvcKoduKAPAK PvcKoduKAPAK PvcKoduKAPAK))(setq doorFlags::p2cFrameThick 55))         
(defun SM249_SETS()(setq doorFlags::p2cDoorSource "INSOURCE")(setq doorFlags::p2cEdges (list PvcKoduKAPAK PvcKoduKAPAK PvcKoduKAPAK PvcKoduKAPAK))(setq doorFlags::p2cFrameThick 55))         
(defun SM371_SETS()(setq doorFlags::p2cDoorSource "INSOURCE")(setq doorFlags::p2cEdges (list PvcKoduKAPAK PvcKoduKAPAK PvcKoduKAPAK PvcKoduKAPAK))(setq doorFlags::p2cFrameThick 55))         
(defun SM456_SETS()(setq doorFlags::p2cDoorSource "INSOURCE")(setq doorFlags::p2cEdges (list PvcKoduKAPAK PvcKoduKAPAK PvcKoduKAPAK PvcKoduKAPAK))(setq doorFlags::p2cFrameThick 55))         
(defun SM100_SETS()(setq doorFlags::p2cDoorSource "INSOURCE")(setq doorFlags::p2cEdges (list PvcKoduKAPAK PvcKoduKAPAK PvcKoduKAPAK PvcKoduKAPAK))(setq doorFlags::p2cFrameThick 55))         
(defun SM101_SETS()(setq doorFlags::p2cDoorSource "INSOURCE")(setq doorFlags::p2cEdges (list PvcKoduKAPAK PvcKoduKAPAK PvcKoduKAPAK PvcKoduKAPAK))(setq doorFlags::p2cFrameThick 55))         
(defun SM102_SETS()(setq doorFlags::p2cDoorSource "INSOURCE")(setq doorFlags::p2cEdges (list PvcKoduKAPAK PvcKoduKAPAK PvcKoduKAPAK PvcKoduKAPAK))(setq doorFlags::p2cFrameThick 55))         
(defun SM103_SETS()(setq doorFlags::p2cDoorSource "INSOURCE")(setq doorFlags::p2cEdges (list PvcKoduKAPAK PvcKoduKAPAK PvcKoduKAPAK PvcKoduKAPAK))(setq doorFlags::p2cFrameThick 55))         
(defun SM107_SETS()(setq doorFlags::p2cDoorSource "INSOURCE")(setq doorFlags::p2cEdges (list PvcKoduKAPAK PvcKoduKAPAK PvcKoduKAPAK PvcKoduKAPAK))(setq doorFlags::p2cFrameThick 55))         
(defun SM108_SETS()(setq doorFlags::p2cDoorSource "INSOURCE")(setq doorFlags::p2cEdges (list PvcKoduKAPAK PvcKoduKAPAK PvcKoduKAPAK PvcKoduKAPAK))(setq doorFlags::p2cFrameThick 55))         
(defun SM109_SETS()(setq doorFlags::p2cDoorSource "INSOURCE")(setq doorFlags::p2cEdges (list PvcKoduKAPAK PvcKoduKAPAK PvcKoduKAPAK PvcKoduKAPAK))(setq doorFlags::p2cFrameThick 55))         
(defun SM110_SETS()(setq doorFlags::p2cDoorSource "INSOURCE")(setq doorFlags::p2cEdges (list PvcKoduKAPAK PvcKoduKAPAK PvcKoduKAPAK PvcKoduKAPAK))(setq doorFlags::p2cFrameThick 55))         
(defun SM111_SETS()(setq doorFlags::p2cDoorSource "INSOURCE")(setq doorFlags::p2cEdges (list PvcKoduKAPAK PvcKoduKAPAK PvcKoduKAPAK PvcKoduKAPAK))(setq doorFlags::p2cFrameThick 55))         
(defun SM112_SETS()(setq doorFlags::p2cDoorSource "INSOURCE")(setq doorFlags::p2cEdges (list PvcKoduKAPAK PvcKoduKAPAK PvcKoduKAPAK PvcKoduKAPAK))(setq doorFlags::p2cFrameThick 55))         
(defun SM113_SETS()(setq doorFlags::p2cDoorSource "INSOURCE")(setq doorFlags::p2cEdges (list PvcKoduKAPAK PvcKoduKAPAK PvcKoduKAPAK PvcKoduKAPAK))(setq doorFlags::p2cFrameThick 55))         
(defun SM116_SETS()(setq doorFlags::p2cDoorSource "INSOURCE")(setq doorFlags::p2cEdges (list PvcKoduKAPAK PvcKoduKAPAK PvcKoduKAPAK PvcKoduKAPAK))(setq doorFlags::p2cFrameThick 55))         
(defun SM118_SETS()(setq doorFlags::p2cDoorSource "INSOURCE")(setq doorFlags::p2cEdges (list PvcKoduKAPAK PvcKoduKAPAK PvcKoduKAPAK PvcKoduKAPAK))(setq doorFlags::p2cFrameThick 55))         
(defun SM119_SETS()(setq doorFlags::p2cDoorSource "INSOURCE")(setq doorFlags::p2cEdges (list PvcKoduKAPAK PvcKoduKAPAK PvcKoduKAPAK PvcKoduKAPAK))(setq doorFlags::p2cFrameThick 55))         
(defun SM120_SETS()(setq doorFlags::p2cDoorSource "INSOURCE")(setq doorFlags::p2cEdges (list PvcKoduKAPAK PvcKoduKAPAK PvcKoduKAPAK PvcKoduKAPAK))(setq doorFlags::p2cFrameThick 55))         
(defun SM121_SETS()(setq doorFlags::p2cDoorSource "INSOURCE")(setq doorFlags::p2cEdges (list PvcKoduKAPAK PvcKoduKAPAK PvcKoduKAPAK PvcKoduKAPAK))(setq doorFlags::p2cFrameThick 55))         
(defun SM122_SETS()(setq doorFlags::p2cDoorSource "INSOURCE")(setq doorFlags::p2cEdges (list PvcKoduKAPAK PvcKoduKAPAK PvcKoduKAPAK PvcKoduKAPAK))(setq doorFlags::p2cFrameThick 55))         
(defun SM123_SETS()(setq doorFlags::p2cDoorSource "INSOURCE")(setq doorFlags::p2cEdges (list PvcKoduKAPAK PvcKoduKAPAK PvcKoduKAPAK PvcKoduKAPAK))(setq doorFlags::p2cFrameThick 55))         
(defun SM124_SETS()(setq doorFlags::p2cDoorSource "INSOURCE")(setq doorFlags::p2cEdges (list PvcKoduKAPAK PvcKoduKAPAK PvcKoduKAPAK PvcKoduKAPAK))(setq doorFlags::p2cFrameThick 55))         
(defun SM125_SETS()(setq doorFlags::p2cDoorSource "INSOURCE")(setq doorFlags::p2cEdges (list PvcKoduKAPAK PvcKoduKAPAK PvcKoduKAPAK PvcKoduKAPAK))(setq doorFlags::p2cFrameThick 55))         
(defun SM128_SETS()(setq doorFlags::p2cDoorSource "INSOURCE")(setq doorFlags::p2cEdges (list PvcKoduKAPAK PvcKoduKAPAK PvcKoduKAPAK PvcKoduKAPAK))(setq doorFlags::p2cFrameThick 55))         
(defun SM144_SETS()(setq doorFlags::p2cDoorSource "INSOURCE")(setq doorFlags::p2cEdges (list PvcKoduKAPAK PvcKoduKAPAK PvcKoduKAPAK PvcKoduKAPAK))(setq doorFlags::p2cFrameThick 55))         
(defun SM148_SETS()(setq doorFlags::p2cDoorSource "INSOURCE")(setq doorFlags::p2cEdges (list PvcKoduKAPAK PvcKoduKAPAK PvcKoduKAPAK PvcKoduKAPAK))(setq doorFlags::p2cFrameThick 55))         
(defun SM150_SETS()(setq doorFlags::p2cDoorSource "INSOURCE")(setq doorFlags::p2cEdges (list PvcKoduKAPAK PvcKoduKAPAK PvcKoduKAPAK PvcKoduKAPAK))(setq doorFlags::p2cFrameThick 55))         
(defun SM152_SETS()(setq doorFlags::p2cDoorSource "INSOURCE")(setq doorFlags::p2cEdges (list PvcKoduKAPAK PvcKoduKAPAK PvcKoduKAPAK PvcKoduKAPAK))(setq doorFlags::p2cFrameThick 55))         
(defun SM155_SETS()(setq doorFlags::p2cDoorSource "INSOURCE")(setq doorFlags::p2cEdges (list PvcKoduKAPAK PvcKoduKAPAK PvcKoduKAPAK PvcKoduKAPAK))(setq doorFlags::p2cFrameThick 55))         
(defun SM170_SETS()(setq doorFlags::p2cDoorSource "INSOURCE")(setq doorFlags::p2cEdges (list PvcKoduKAPAK PvcKoduKAPAK PvcKoduKAPAK PvcKoduKAPAK))(setq doorFlags::p2cFrameThick 55))         
(defun SM171_SETS()(setq doorFlags::p2cDoorSource "INSOURCE")(setq doorFlags::p2cEdges (list PvcKoduKAPAK PvcKoduKAPAK PvcKoduKAPAK PvcKoduKAPAK))(setq doorFlags::p2cFrameThick 55))         
(defun SM172_SETS()(setq doorFlags::p2cDoorSource "INSOURCE")(setq doorFlags::p2cEdges (list PvcKoduKAPAK PvcKoduKAPAK PvcKoduKAPAK PvcKoduKAPAK))(setq doorFlags::p2cFrameThick 55))         
(defun SM173_SETS()(setq doorFlags::p2cDoorSource "INSOURCE")(setq doorFlags::p2cEdges (list PvcKoduKAPAK PvcKoduKAPAK PvcKoduKAPAK PvcKoduKAPAK))(setq doorFlags::p2cFrameThick 55))         
(defun SM174_SETS()(setq doorFlags::p2cDoorSource "INSOURCE")(setq doorFlags::p2cEdges (list PvcKoduKAPAK PvcKoduKAPAK PvcKoduKAPAK PvcKoduKAPAK))(setq doorFlags::p2cFrameThick 55))         
(defun SM175_SETS()(setq doorFlags::p2cDoorSource "INSOURCE")(setq doorFlags::p2cEdges (list PvcKoduKAPAK PvcKoduKAPAK PvcKoduKAPAK PvcKoduKAPAK))(setq doorFlags::p2cFrameThick 55))         
(defun SM178_SETS()(setq doorFlags::p2cDoorSource "INSOURCE")(setq doorFlags::p2cEdges (list PvcKoduKAPAK PvcKoduKAPAK PvcKoduKAPAK PvcKoduKAPAK))(setq doorFlags::p2cFrameThick 55))         
(defun SM179_SETS()(setq doorFlags::p2cDoorSource "INSOURCE")(setq doorFlags::p2cEdges (list PvcKoduKAPAK PvcKoduKAPAK PvcKoduKAPAK PvcKoduKAPAK))(setq doorFlags::p2cFrameThick 55))         
(defun SM180_SETS()(setq doorFlags::p2cDoorSource "INSOURCE")(setq doorFlags::p2cEdges (list PvcKoduKAPAK PvcKoduKAPAK PvcKoduKAPAK PvcKoduKAPAK))(setq doorFlags::p2cFrameThick 55))         
(defun SM181_SETS()(setq doorFlags::p2cDoorSource "INSOURCE")(setq doorFlags::p2cEdges (list PvcKoduKAPAK PvcKoduKAPAK PvcKoduKAPAK PvcKoduKAPAK))(setq doorFlags::p2cFrameThick 55))         
(defun SM182_SETS()(setq doorFlags::p2cDoorSource "INSOURCE")(setq doorFlags::p2cEdges (list PvcKoduKAPAK PvcKoduKAPAK PvcKoduKAPAK PvcKoduKAPAK))(setq doorFlags::p2cFrameThick 55))         
(defun SM184_SETS()(setq doorFlags::p2cDoorSource "INSOURCE")(setq doorFlags::p2cEdges (list PvcKoduKAPAK PvcKoduKAPAK PvcKoduKAPAK PvcKoduKAPAK))(setq doorFlags::p2cFrameThick 55))         
(defun SM185_SETS()(setq doorFlags::p2cDoorSource "INSOURCE")(setq doorFlags::p2cEdges (list PvcKoduKAPAK PvcKoduKAPAK PvcKoduKAPAK PvcKoduKAPAK))(setq doorFlags::p2cFrameThick 55))         
(defun SM186_SETS()(setq doorFlags::p2cDoorSource "INSOURCE")(setq doorFlags::p2cEdges (list PvcKoduKAPAK PvcKoduKAPAK PvcKoduKAPAK PvcKoduKAPAK))(setq doorFlags::p2cFrameThick 55))         
(defun SM187_SETS()(setq doorFlags::p2cDoorSource "INSOURCE")(setq doorFlags::p2cEdges (list PvcKoduKAPAK PvcKoduKAPAK PvcKoduKAPAK PvcKoduKAPAK))(setq doorFlags::p2cFrameThick 55))         
(defun SM189_SETS()(setq doorFlags::p2cDoorSource "INSOURCE")(setq doorFlags::p2cEdges (list PvcKoduKAPAK PvcKoduKAPAK PvcKoduKAPAK PvcKoduKAPAK))(setq doorFlags::p2cFrameThick 55))         
(defun SM191_SETS()(setq doorFlags::p2cDoorSource "INSOURCE")(setq doorFlags::p2cEdges (list PvcKoduKAPAK PvcKoduKAPAK PvcKoduKAPAK PvcKoduKAPAK))(setq doorFlags::p2cFrameThick 55))         
(defun SM192_SETS()(setq doorFlags::p2cDoorSource "INSOURCE")(setq doorFlags::p2cEdges (list PvcKoduKAPAK PvcKoduKAPAK PvcKoduKAPAK PvcKoduKAPAK))(setq doorFlags::p2cFrameThick 55))         
(defun SM194_SETS()(setq doorFlags::p2cDoorSource "INSOURCE")(setq doorFlags::p2cEdges (list PvcKoduKAPAK PvcKoduKAPAK PvcKoduKAPAK PvcKoduKAPAK))(setq doorFlags::p2cFrameThick 55))         
(defun SM195_SETS()(setq doorFlags::p2cDoorSource "INSOURCE")(setq doorFlags::p2cEdges (list PvcKoduKAPAK PvcKoduKAPAK PvcKoduKAPAK PvcKoduKAPAK))(setq doorFlags::p2cFrameThick 55))         
(defun SM196_SETS()(setq doorFlags::p2cDoorSource "INSOURCE")(setq doorFlags::p2cEdges (list PvcKoduKAPAK PvcKoduKAPAK PvcKoduKAPAK PvcKoduKAPAK))(setq doorFlags::p2cFrameThick 55))         
(defun SM197_SETS()(setq doorFlags::p2cDoorSource "INSOURCE")(setq doorFlags::p2cEdges (list PvcKoduKAPAK PvcKoduKAPAK PvcKoduKAPAK PvcKoduKAPAK))(setq doorFlags::p2cFrameThick 55))         
(defun SM198_SETS()(setq doorFlags::p2cDoorSource "INSOURCE")(setq doorFlags::p2cEdges (list PvcKoduKAPAK PvcKoduKAPAK PvcKoduKAPAK PvcKoduKAPAK))(setq doorFlags::p2cFrameThick 55))         
(defun SM200_SETS()(setq doorFlags::p2cDoorSource "INSOURCE")(setq doorFlags::p2cEdges (list PvcKoduKAPAK PvcKoduKAPAK PvcKoduKAPAK PvcKoduKAPAK))(setq doorFlags::p2cFrameThick 55))         
(defun SM203_SETS()(setq doorFlags::p2cDoorSource "INSOURCE")(setq doorFlags::p2cEdges (list PvcKoduKAPAK PvcKoduKAPAK PvcKoduKAPAK PvcKoduKAPAK))(setq doorFlags::p2cFrameThick 55))         
(defun SM204_SETS()(setq doorFlags::p2cDoorSource "INSOURCE")(setq doorFlags::p2cEdges (list PvcKoduKAPAK PvcKoduKAPAK PvcKoduKAPAK PvcKoduKAPAK))(setq doorFlags::p2cFrameThick 55))         
(defun SM205_SETS()(setq doorFlags::p2cDoorSource "INSOURCE")(setq doorFlags::p2cEdges (list PvcKoduKAPAK PvcKoduKAPAK PvcKoduKAPAK PvcKoduKAPAK))(setq doorFlags::p2cFrameThick 55))         
(defun SM206_SETS()(setq doorFlags::p2cDoorSource "INSOURCE")(setq doorFlags::p2cEdges (list PvcKoduKAPAK PvcKoduKAPAK PvcKoduKAPAK PvcKoduKAPAK))(setq doorFlags::p2cFrameThick 55))         
(defun SM207_SETS()(setq doorFlags::p2cDoorSource "INSOURCE")(setq doorFlags::p2cEdges (list PvcKoduKAPAK PvcKoduKAPAK PvcKoduKAPAK PvcKoduKAPAK))(setq doorFlags::p2cFrameThick 55))         
(defun SM208_SETS()(setq doorFlags::p2cDoorSource "INSOURCE")(setq doorFlags::p2cEdges (list PvcKoduKAPAK PvcKoduKAPAK PvcKoduKAPAK PvcKoduKAPAK))(setq doorFlags::p2cFrameThick 55))         
(defun SM209_SETS()(setq doorFlags::p2cDoorSource "INSOURCE")(setq doorFlags::p2cEdges (list PvcKoduKAPAK PvcKoduKAPAK PvcKoduKAPAK PvcKoduKAPAK))(setq doorFlags::p2cFrameThick 55))         
(defun SM210_SETS()(setq doorFlags::p2cDoorSource "INSOURCE")(setq doorFlags::p2cEdges (list PvcKoduKAPAK PvcKoduKAPAK PvcKoduKAPAK PvcKoduKAPAK))(setq doorFlags::p2cFrameThick 55))         
(defun SM211_SETS()(setq doorFlags::p2cDoorSource "INSOURCE")(setq doorFlags::p2cEdges (list PvcKoduKAPAK PvcKoduKAPAK PvcKoduKAPAK PvcKoduKAPAK))(setq doorFlags::p2cFrameThick 55))         
(defun SM212_SETS()(setq doorFlags::p2cDoorSource "INSOURCE")(setq doorFlags::p2cEdges (list PvcKoduKAPAK PvcKoduKAPAK PvcKoduKAPAK PvcKoduKAPAK))(setq doorFlags::p2cFrameThick 55))         
(defun SM213_SETS()(setq doorFlags::p2cDoorSource "INSOURCE")(setq doorFlags::p2cEdges (list PvcKoduKAPAK PvcKoduKAPAK PvcKoduKAPAK PvcKoduKAPAK))(setq doorFlags::p2cFrameThick 55))         
(defun SM214_SETS()(setq doorFlags::p2cDoorSource "INSOURCE")(setq doorFlags::p2cEdges (list PvcKoduKAPAK PvcKoduKAPAK PvcKoduKAPAK PvcKoduKAPAK))(setq doorFlags::p2cFrameThick 55))         
(defun SM216_SETS()(setq doorFlags::p2cDoorSource "INSOURCE")(setq doorFlags::p2cEdges (list PvcKoduKAPAK PvcKoduKAPAK PvcKoduKAPAK PvcKoduKAPAK))(setq doorFlags::p2cFrameThick 55))         
(defun SM217_SETS()(setq doorFlags::p2cDoorSource "INSOURCE")(setq doorFlags::p2cEdges (list PvcKoduKAPAK PvcKoduKAPAK PvcKoduKAPAK PvcKoduKAPAK))(setq doorFlags::p2cFrameThick 55))         
(defun SM218_SETS()(setq doorFlags::p2cDoorSource "INSOURCE")(setq doorFlags::p2cEdges (list PvcKoduKAPAK PvcKoduKAPAK PvcKoduKAPAK PvcKoduKAPAK))(setq doorFlags::p2cFrameThick 55))         
(defun SM222_SETS()(setq doorFlags::p2cDoorSource "INSOURCE")(setq doorFlags::p2cEdges (list PvcKoduKAPAK PvcKoduKAPAK PvcKoduKAPAK PvcKoduKAPAK))(setq doorFlags::p2cFrameThick 55))         
(defun SM233_SETS()(setq doorFlags::p2cDoorSource "INSOURCE")(setq doorFlags::p2cEdges (list PvcKoduKAPAK PvcKoduKAPAK PvcKoduKAPAK PvcKoduKAPAK))(setq doorFlags::p2cFrameThick 55))         
(defun SM244_SETS()(setq doorFlags::p2cDoorSource "INSOURCE")(setq doorFlags::p2cEdges (list PvcKoduKAPAK PvcKoduKAPAK PvcKoduKAPAK PvcKoduKAPAK))(setq doorFlags::p2cFrameThick 55))         
(defun SM248_SETS()(setq doorFlags::p2cDoorSource "INSOURCE")(setq doorFlags::p2cEdges (list PvcKoduKAPAK PvcKoduKAPAK PvcKoduKAPAK PvcKoduKAPAK))(setq doorFlags::p2cFrameThick 55))         
(defun SM249_SETS()(setq doorFlags::p2cDoorSource "INSOURCE")(setq doorFlags::p2cEdges (list PvcKoduKAPAK PvcKoduKAPAK PvcKoduKAPAK PvcKoduKAPAK))(setq doorFlags::p2cFrameThick 55))         
(defun SM259_SETS()(setq doorFlags::p2cDoorSource "INSOURCE")(setq doorFlags::p2cEdges (list PvcKoduKAPAK PvcKoduKAPAK PvcKoduKAPAK PvcKoduKAPAK))(setq doorFlags::p2cFrameThick 55))         
(defun SM266_SETS()(setq doorFlags::p2cDoorSource "INSOURCE")(setq doorFlags::p2cEdges (list PvcKoduKAPAK PvcKoduKAPAK PvcKoduKAPAK PvcKoduKAPAK))(setq doorFlags::p2cFrameThick 55))         
(defun SM267_SETS()(setq doorFlags::p2cDoorSource "INSOURCE")(setq doorFlags::p2cEdges (list PvcKoduKAPAK PvcKoduKAPAK PvcKoduKAPAK PvcKoduKAPAK))(setq doorFlags::p2cFrameThick 55))         
(defun SM268_SETS()(setq doorFlags::p2cDoorSource "INSOURCE")(setq doorFlags::p2cEdges (list PvcKoduKAPAK PvcKoduKAPAK PvcKoduKAPAK PvcKoduKAPAK))(setq doorFlags::p2cFrameThick 55))         
(defun SM274_SETS()(setq doorFlags::p2cDoorSource "INSOURCE")(setq doorFlags::p2cEdges (list PvcKoduKAPAK PvcKoduKAPAK PvcKoduKAPAK PvcKoduKAPAK))(setq doorFlags::p2cFrameThick 55))         
(defun SM340_SETS()(setq doorFlags::p2cDoorSource "INSOURCE")(setq doorFlags::p2cEdges (list PvcKoduKAPAK PvcKoduKAPAK PvcKoduKAPAK PvcKoduKAPAK))(setq doorFlags::p2cFrameThick 55))         
(defun SM343_SETS()(setq doorFlags::p2cDoorSource "INSOURCE")(setq doorFlags::p2cEdges (list PvcKoduKAPAK PvcKoduKAPAK PvcKoduKAPAK PvcKoduKAPAK))(setq doorFlags::p2cFrameThick 55))         
(defun SM371_SETS()(setq doorFlags::p2cDoorSource "INSOURCE")(setq doorFlags::p2cEdges (list PvcKoduKAPAK PvcKoduKAPAK PvcKoduKAPAK PvcKoduKAPAK))(setq doorFlags::p2cFrameThick 55))         
(defun SM381_SETS()(setq doorFlags::p2cDoorSource "INSOURCE")(setq doorFlags::p2cEdges (list PvcKoduKAPAK PvcKoduKAPAK PvcKoduKAPAK PvcKoduKAPAK))(setq doorFlags::p2cFrameThick 55))         
(defun SM401_SETS()(setq doorFlags::p2cDoorSource "INSOURCE")(setq doorFlags::p2cEdges (list PvcKoduKAPAK PvcKoduKAPAK PvcKoduKAPAK PvcKoduKAPAK))(setq doorFlags::p2cFrameThick 55))         
(defun SM402_SETS()(setq doorFlags::p2cDoorSource "INSOURCE")(setq doorFlags::p2cEdges (list PvcKoduKAPAK PvcKoduKAPAK PvcKoduKAPAK PvcKoduKAPAK))(setq doorFlags::p2cFrameThick 55))         
(defun SM407_SETS()(setq doorFlags::p2cDoorSource "INSOURCE")(setq doorFlags::p2cEdges (list PvcKoduKAPAK PvcKoduKAPAK PvcKoduKAPAK PvcKoduKAPAK))(setq doorFlags::p2cFrameThick 55))         
(defun SM430_SETS()(setq doorFlags::p2cDoorSource "INSOURCE")(setq doorFlags::p2cEdges (list PvcKoduKAPAK PvcKoduKAPAK PvcKoduKAPAK PvcKoduKAPAK))(setq doorFlags::p2cFrameThick 55))         
(defun SM432_SETS()(setq doorFlags::p2cDoorSource "INSOURCE")(setq doorFlags::p2cEdges (list PvcKoduKAPAK PvcKoduKAPAK PvcKoduKAPAK PvcKoduKAPAK))(setq doorFlags::p2cFrameThick 55))         
(defun SM434_SETS()(setq doorFlags::p2cDoorSource "INSOURCE")(setq doorFlags::p2cEdges (list PvcKoduKAPAK PvcKoduKAPAK PvcKoduKAPAK PvcKoduKAPAK))(setq doorFlags::p2cFrameThick 55))         
(defun SM438_SETS()(setq doorFlags::p2cDoorSource "INSOURCE")(setq doorFlags::p2cEdges (list PvcKoduKAPAK PvcKoduKAPAK PvcKoduKAPAK PvcKoduKAPAK))(setq doorFlags::p2cFrameThick 55))         
(defun SM440_SETS()(setq doorFlags::p2cDoorSource "INSOURCE")(setq doorFlags::p2cEdges (list PvcKoduKAPAK PvcKoduKAPAK PvcKoduKAPAK PvcKoduKAPAK))(setq doorFlags::p2cFrameThick 55))         
(defun SM442_SETS()(setq doorFlags::p2cDoorSource "INSOURCE")(setq doorFlags::p2cEdges (list PvcKoduKAPAK PvcKoduKAPAK PvcKoduKAPAK PvcKoduKAPAK))(setq doorFlags::p2cFrameThick 55))         
(defun SM444_SETS()(setq doorFlags::p2cDoorSource "INSOURCE")(setq doorFlags::p2cEdges (list PvcKoduKAPAK PvcKoduKAPAK PvcKoduKAPAK PvcKoduKAPAK))(setq doorFlags::p2cFrameThick 55))         
(defun SM446_SETS()(setq doorFlags::p2cDoorSource "INSOURCE")(setq doorFlags::p2cEdges (list PvcKoduKAPAK PvcKoduKAPAK PvcKoduKAPAK PvcKoduKAPAK))(setq doorFlags::p2cFrameThick 55))         
(defun SM450_SETS()(setq doorFlags::p2cDoorSource "INSOURCE")(setq doorFlags::p2cEdges (list PvcKoduKAPAK PvcKoduKAPAK PvcKoduKAPAK PvcKoduKAPAK))(setq doorFlags::p2cFrameThick 55))         
(defun SM454_SETS()(setq doorFlags::p2cDoorSource "INSOURCE")(setq doorFlags::p2cEdges (list PvcKoduKAPAK PvcKoduKAPAK PvcKoduKAPAK PvcKoduKAPAK))(setq doorFlags::p2cFrameThick 55))         
(defun SM456_SETS()(setq doorFlags::p2cDoorSource "INSOURCE")(setq doorFlags::p2cEdges (list PvcKoduKAPAK PvcKoduKAPAK PvcKoduKAPAK PvcKoduKAPAK))(setq doorFlags::p2cFrameThick 55))         
(defun SM464_SETS()(setq doorFlags::p2cDoorSource "INSOURCE")(setq doorFlags::p2cEdges (list PvcKoduKAPAK PvcKoduKAPAK PvcKoduKAPAK PvcKoduKAPAK))(setq doorFlags::p2cFrameThick 55))         
(defun SM448_SETS()(setq doorFlags::p2cDoorSource "INSOURCE")(setq doorFlags::p2cEdges (list PvcKoduKAPAK PvcKoduKAPAK PvcKoduKAPAK PvcKoduKAPAK))(setq doorFlags::p2cFrameThick 55))         
(defun SM602_SETS()(setq doorFlags::p2cDoorSource "INSOURCE")(setq doorFlags::p2cEdges (list PvcKoduKAPAK PvcKoduKAPAK PvcKoduKAPAK PvcKoduKAPAK))(setq doorFlags::p2cFrameThick 55))         
(defun SM605_SETS()(setq doorFlags::p2cDoorSource "INSOURCE")(setq doorFlags::p2cEdges (list PvcKoduKAPAK PvcKoduKAPAK PvcKoduKAPAK PvcKoduKAPAK))(setq doorFlags::p2cFrameThick 55))         
(defun SM720_SETS()(setq doorFlags::p2cDoorSource "INSOURCE")(setq doorFlags::p2cEdges (list PvcKoduKAPAK PvcKoduKAPAK PvcKoduKAPAK PvcKoduKAPAK))(setq doorFlags::p2cFrameThick 55))         
(defun SMMITRA_SETS()(setq doorFlags::p2cDoorSource "INSOURCE")(setq doorFlags::p2cEdges (list PvcKoduKAPAK PvcKoduKAPAK PvcKoduKAPAK PvcKoduKAPAK))(setq doorFlags::p2cFrameThick 55))       
(defun SM203VSTK_SETS()(setq doorFlags::p2cDoorSource "INSOURCE")(setq doorFlags::p2cEdges (list PvcKoduKAPAK PvcKoduKAPAK PvcKoduKAPAK PvcKoduKAPAK))(setq doorFlags::p2cFrameThick 55))     
(defun SM217VSTK_SETS()(setq doorFlags::p2cDoorSource "INSOURCE")(setq doorFlags::p2cEdges (list PvcKoduKAPAK PvcKoduKAPAK PvcKoduKAPAK PvcKoduKAPAK))(setq doorFlags::p2cFrameThick 55))     
(defun SM222VSTK_SETS()(setq doorFlags::p2cDoorSource "INSOURCE")(setq doorFlags::p2cEdges (list PvcKoduKAPAK PvcKoduKAPAK PvcKoduKAPAK PvcKoduKAPAK))(setq doorFlags::p2cFrameThick 55))     
(defun SM244VSTK_SETS()(setq doorFlags::p2cDoorSource "INSOURCE")(setq doorFlags::p2cEdges (list PvcKoduKAPAK PvcKoduKAPAK PvcKoduKAPAK PvcKoduKAPAK))(setq doorFlags::p2cFrameThick 55))     
(defun SM248VSTK_SETS()(setq doorFlags::p2cDoorSource "INSOURCE")(setq doorFlags::p2cEdges (list PvcKoduKAPAK PvcKoduKAPAK PvcKoduKAPAK PvcKoduKAPAK))(setq doorFlags::p2cFrameThick 55))     
(defun SM259VSTK_SETS()(setq doorFlags::p2cDoorSource "INSOURCE")(setq doorFlags::p2cEdges (list PvcKoduKAPAK PvcKoduKAPAK PvcKoduKAPAK PvcKoduKAPAK))(setq doorFlags::p2cFrameThick 55))     
(defun SM266VSTK_SETS()(setq doorFlags::p2cDoorSource "INSOURCE")(setq doorFlags::p2cEdges (list PvcKoduKAPAK PvcKoduKAPAK PvcKoduKAPAK PvcKoduKAPAK))(setq doorFlags::p2cFrameThick 55))     
(defun SM267VSTK_SETS()(setq doorFlags::p2cDoorSource "INSOURCE")(setq doorFlags::p2cEdges (list PvcKoduKAPAK PvcKoduKAPAK PvcKoduKAPAK PvcKoduKAPAK))(setq doorFlags::p2cFrameThick 55))     
(defun SM268VSTK_SETS()(setq doorFlags::p2cDoorSource "INSOURCE")(setq doorFlags::p2cEdges (list PvcKoduKAPAK PvcKoduKAPAK PvcKoduKAPAK PvcKoduKAPAK))(setq doorFlags::p2cFrameThick 55))     
(defun SM274VSTK_SETS()(setq doorFlags::p2cDoorSource "INSOURCE")(setq doorFlags::p2cEdges (list PvcKoduKAPAK PvcKoduKAPAK PvcKoduKAPAK PvcKoduKAPAK))(setq doorFlags::p2cFrameThick 55))     
(defun SM340VSTK_SETS()(setq doorFlags::p2cDoorSource "INSOURCE")(setq doorFlags::p2cEdges (list PvcKoduKAPAK PvcKoduKAPAK PvcKoduKAPAK PvcKoduKAPAK))(setq doorFlags::p2cFrameThick 55))     
(defun SM343VSTK_SETS()(setq doorFlags::p2cDoorSource "INSOURCE")(setq doorFlags::p2cEdges (list PvcKoduKAPAK PvcKoduKAPAK PvcKoduKAPAK PvcKoduKAPAK))(setq doorFlags::p2cFrameThick 55))     
(defun SM381VSTK_SETS()(setq doorFlags::p2cDoorSource "INSOURCE")(setq doorFlags::p2cEdges (list PvcKoduKAPAK PvcKoduKAPAK PvcKoduKAPAK PvcKoduKAPAK))(setq doorFlags::p2cFrameThick 55))     
(defun SM602VSTK_SETS()(setq doorFlags::p2cDoorSource "INSOURCE")(setq doorFlags::p2cEdges (list PvcKoduKAPAK PvcKoduKAPAK PvcKoduKAPAK PvcKoduKAPAK))(setq doorFlags::p2cFrameThick 55))     
(defun SMMITRAVSTK_SETS()(setq doorFlags::p2cDoorSource "INSOURCE")(setq doorFlags::p2cEdges (list PvcKoduKAPAK PvcKoduKAPAK PvcKoduKAPAK PvcKoduKAPAK))(setq doorFlags::p2cFrameThick 55))   
(defun SMLIBERTAVSTK_SETS()(setq doorFlags::p2cDoorSource "INSOURCE")(setq doorFlags::p2cEdges (list PvcKoduKAPAK PvcKoduKAPAK PvcKoduKAPAK PvcKoduKAPAK))(setq doorFlags::p2cFrameThick 55)) 
(defun CM02_SETS()(setq doorFlags::p2cDoorSource "INSOURCE")(setq doorFlags::p2cEdges (list PvcKoduKAPAK PvcKoduKAPAK PvcKoduKAPAK PvcKoduKAPAK))(setq doorFlags::p2cFrameThick 55))          
(defun CM04_SETS()(setq doorFlags::p2cDoorSource "INSOURCE")(setq doorFlags::p2cEdges (list PvcKoduKAPAK PvcKoduKAPAK PvcKoduKAPAK PvcKoduKAPAK))(setq doorFlags::p2cFrameThick 55))          
(defun CM05_SETS()(setq doorFlags::p2cDoorSource "INSOURCE")(setq doorFlags::p2cEdges (list PvcKoduKAPAK PvcKoduKAPAK PvcKoduKAPAK PvcKoduKAPAK))(setq doorFlags::p2cFrameThick 55))          
(defun CM06_SETS()(setq doorFlags::p2cDoorSource "INSOURCE")(setq doorFlags::p2cEdges (list PvcKoduKAPAK PvcKoduKAPAK PvcKoduKAPAK PvcKoduKAPAK))(setq doorFlags::p2cFrameThick 55))          
(defun CM07_SETS()(setq doorFlags::p2cDoorSource "INSOURCE")(setq doorFlags::p2cEdges (list PvcKoduKAPAK PvcKoduKAPAK PvcKoduKAPAK PvcKoduKAPAK))(setq doorFlags::p2cFrameThick 55))          
(defun CM09_SETS()(setq doorFlags::p2cDoorSource "INSOURCE")(setq doorFlags::p2cEdges (list PvcKoduKAPAK PvcKoduKAPAK PvcKoduKAPAK PvcKoduKAPAK))(setq doorFlags::p2cFrameThick 55))          
(defun CM10_SETS()(setq doorFlags::p2cDoorSource "INSOURCE")(setq doorFlags::p2cEdges (list PvcKoduKAPAK PvcKoduKAPAK PvcKoduKAPAK PvcKoduKAPAK))(setq doorFlags::p2cFrameThick 55))          
(defun CM12_SETS()(setq doorFlags::p2cDoorSource "INSOURCE")(setq doorFlags::p2cEdges (list PvcKoduKAPAK PvcKoduKAPAK PvcKoduKAPAK PvcKoduKAPAK))(setq doorFlags::p2cFrameThick 55))          
(defun CM14_SETS()(setq doorFlags::p2cDoorSource "INSOURCE")(setq doorFlags::p2cEdges (list PvcKoduKAPAK PvcKoduKAPAK PvcKoduKAPAK PvcKoduKAPAK))(setq doorFlags::p2cFrameThick 55))          
(defun BMB72_SETS()(setq doorFlags::p2cDoorSource "INSOURCE")(setq doorFlags::p2cEdges (list PvcKoduKAPAK PvcKoduKAPAK PvcKoduKAPAK PvcKoduKAPAK))(setq doorFlags::p2cFrameThick 55))         
(defun BMB60_SETS()(setq doorFlags::p2cDoorSource "INSOURCE")(setq doorFlags::p2cEdges (list PvcKoduKAPAK PvcKoduKAPAK PvcKoduKAPAK PvcKoduKAPAK))(setq doorFlags::p2cFrameThick 55))         
(defun BMB36_SETS()(setq doorFlags::p2cDoorSource "INSOURCE")(setq doorFlags::p2cEdges (list PvcKoduKAPAK PvcKoduKAPAK PvcKoduKAPAK PvcKoduKAPAK))(setq doorFlags::p2cFrameThick 55))         
(defun KPK36Str_SETS()(setq doorFlags::p2cDoorSource "INSOURCE")(setq doorFlags::p2cEdges (list PvcKoduKAPAK PvcKoduKAPAK PvcKoduKAPAK PvcKoduKAPAK))(setq doorFlags::p2cFrameThick 55))      
(defun CTL6K_SETS()(setq doorFlags::p2cDoorSource "INSOURCE")(setq doorFlags::p2cEdges (list PvcKoduKAPAK PvcKoduKAPAK PvcKoduKAPAK PvcKoduKAPAK))(setq doorFlags::p2cFrameThick 55))         
(defun WRDOOR1_SETS()(setq doorFlags::p2cDoorSource "INSOURCE")(setq doorFlags::p2cEdges (list PvcKoduKAPAK PvcKoduKAPAK PvcKoduKAPAK PvcKoduKAPAK))(setq doorFlags::p2cFrameThick 55))       
(defun WRDOOR2_SETS()(setq doorFlags::p2cDoorSource "INSOURCE")(setq doorFlags::p2cEdges (list PvcKoduKAPAK PvcKoduKAPAK PvcKoduKAPAK PvcKoduKAPAK))(setq doorFlags::p2cFrameThick 55))       
(defun WRDOOR3_SETS()(setq doorFlags::p2cDoorSource "INSOURCE")(setq doorFlags::p2cEdges (list PvcKoduKAPAK PvcKoduKAPAK PvcKoduKAPAK PvcKoduKAPAK))(setq doorFlags::p2cFrameThick 55))       
(defun WRDOOR3G_SETS()(setq doorFlags::p2cDoorSource "INSOURCE")(setq doorFlags::p2cEdges (list PvcKoduKAPAK PvcKoduKAPAK PvcKoduKAPAK PvcKoduKAPAK))(setq doorFlags::p2cFrameThick 55))      
(defun WRDOORC1_SETS()(setq doorFlags::p2cDoorSource "INSOURCE")(setq doorFlags::p2cEdges (list PvcKoduKAPAK PvcKoduKAPAK PvcKoduKAPAK PvcKoduKAPAK))(setq doorFlags::p2cFrameThick 55))      
(defun WRDOORC2_SETS()(setq doorFlags::p2cDoorSource "INSOURCE")(setq doorFlags::p2cEdges (list PvcKoduKAPAK PvcKoduKAPAK PvcKoduKAPAK PvcKoduKAPAK))(setq doorFlags::p2cFrameThick 55))      
(defun WRDOORC3_SETS()(setq doorFlags::p2cDoorSource "INSOURCE")(setq doorFlags::p2cEdges (list PvcKoduKAPAK PvcKoduKAPAK PvcKoduKAPAK PvcKoduKAPAK))(setq doorFlags::p2cFrameThick 55))      
(defun VK0000_SETS()(setq doorFlags::p2cDoorSource "INSOURCE")(setq doorFlags::p2cEdges (list PvcKoduKAPAK PvcKoduKAPAK PvcKoduKAPAK PvcKoduKAPAK))(setq doorFlags::p2cFrameThick 55))        
(defun ROMA1_SETS()(setq doorFlags::p2cDoorSource "INSOURCE")(setq doorFlags::p2cEdges (list PvcKoduKAPAK PvcKoduKAPAK PvcKoduKAPAK PvcKoduKAPAK))(setq doorFlags::p2cFrameThick 55))         
(defun ROMA2_SETS()(setq doorFlags::p2cDoorSource "INSOURCE")(setq doorFlags::p2cEdges (list PvcKoduKAPAK PvcKoduKAPAK PvcKoduKAPAK PvcKoduKAPAK))(setq doorFlags::p2cFrameThick 55))         
(defun P0D10_SETS()(setq doorFlags::p2cDoorSource "INSOURCE")(setq doorFlags::p2cEdges (list PvcKoduKAPAK PvcKoduKAPAK PvcKoduKAPAK PvcKoduKAPAK))(setq doorFlags::p2cFrameThick 55))         
(defun AYNA_SETS()(setq doorFlags::p2cDoorSource "INSOURCE")(setq doorFlags::p2cEdges (list PvcKoduKAPAK PvcKoduKAPAK PvcKoduKAPAK PvcKoduKAPAK))(setq doorFlags::p2cFrameThick 55))          
(defun VSTX01_SETS()(setq doorFlags::p2cDoorSource "INSOURCE")(setq doorFlags::p2cEdges (list PvcKoduKAPAK PvcKoduKAPAK PvcKoduKAPAK PvcKoduKAPAK))(setq doorFlags::p2cFrameThick 55))        
(defun VSTX02_SETS()(setq doorFlags::p2cDoorSource "INSOURCE")(setq doorFlags::p2cEdges (list PvcKoduKAPAK PvcKoduKAPAK PvcKoduKAPAK PvcKoduKAPAK))(setq doorFlags::p2cFrameThick 55))        
(defun CIT_SETS()(setq doorFlags::p2cDoorSource "INSOURCE")(setq doorFlags::p2cEdges (list PvcKoduKAPAK PvcKoduKAPAK PvcKoduKAPAK PvcKoduKAPAK))(setq doorFlags::p2cFrameThick 55))           
(defun GOMMEKPK_SETS()(setq doorFlags::p2cDoorSource "INSOURCE")(setq doorFlags::p2cEdges (list PvcKoduKAPAK PvcKoduKAPAK PvcKoduKAPAK PvcKoduKAPAK))(setq doorFlags::p2cFrameThick 55))      
(defun KDALGA_SETS()(setq doorFlags::p2cDoorSource "INSOURCE")(setq doorFlags::p2cEdges (list PvcKoduKAPAK PvcKoduKAPAK PvcKoduKAPAK PvcKoduKAPAK))(setq doorFlags::p2cFrameThick 55))       
(defun BDALGA_SETS()(setq doorFlags::p2cDoorSource "INSOURCE")(setq doorFlags::p2cEdges (list PvcKoduKAPAK PvcKoduKAPAK PvcKoduKAPAK PvcKoduKAPAK))(setq doorFlags::p2cFrameThick 55))       

;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
; 																				FITZGERALD DOORS
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;

(defun KAPAK104_SETS ()
	(setq doorFlags::p2cDoorSource "(list \"##\" 22.0)")
	(setq doorFlags::p2cEdges (list PvcKoduKAPAK PvcKoduKAPAK PvcKoduKAPAK PvcKoduKAPAK))
	(setq doorFlags::p2cFrameThick 55)
)     

;__________________________________________________________________________________________________________________________________________________________

(defun DUZKPK_AKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "DUZKPK" "_" x "KANATSETS")) DUZKPK_AKANATSETS) ) _KSets_typeAList)

(defun DUZKPK_BKANATSETS(x z)
	(setq doorFlags::p2cDoorSource "INSOURCE")
	(setq doorFlags::p2cEdges (list PvcKoduKAPAK PvcKoduKAPAK PvcKoduKAPAK PvcKoduKAPAK))
	(setq doorFlags::p2cFrameThick 55)
)
(mapcar '(lambda (x) (set (read (strcat "DUZKPK" "_" x "KANATSETS")) DUZKPK_BKANATSETS) ) _KSets_typeBList)

;__________________________________________________________________________________________________________________________________________________________

; (defun DIMHOR_SETS()(setq doorFlags::p2cDoorSource "INSOURCE")(setq doorFlags::p2cEdges (list PvcKoduKAPAK PvcKoduKAPAK PvcKoduKAPAK PvcKoduKAPAK))(setq doorFlags::p2cFrameThick 55))       
; (defun DUZDIK_SETS()(setq doorFlags::p2cDoorSource "INSOURCE")(setq doorFlags::p2cEdges (list PvcKoduKAPAK PvcKoduKAPAK PvcKoduKAPAK PvcKoduKAPAK))(setq doorFlags::p2cFrameThick 55))       
; (defun KDALGA_SETS()(setq doorFlags::p2cDoorSource "INSOURCE")(setq doorFlags::p2cEdges (list PvcKoduKAPAK PvcKoduKAPAK PvcKoduKAPAK PvcKoduKAPAK))(setq doorFlags::p2cFrameThick 55))       
; (defun BDALGA_SETS()(setq doorFlags::p2cDoorSource "INSOURCE")(setq doorFlags::p2cEdges (list PvcKoduKAPAK PvcKoduKAPAK PvcKoduKAPAK PvcKoduKAPAK))(setq doorFlags::p2cFrameThick 55))
