(defun reverseMatRot(mainEnt / recentRot newRot)
	(setq recentRot (grx_getmaterial_rotation mainEnt))
	(setq matRot (ifnull recentRot 0.0))
	(if
		(setq newRot
			(cond
				((equal matRot 0.0) 90.0)
				((equal matRot 90.0) 0.0)
			)
		)
		(progn
			(grx_setmaterial_rotation mainEnt newRot)
			(redraw)
		)
	)
)

(defun mtzg (dummyKod dummyParams / TK20_W2 unitW unitd TK20_D1 kodBlock TK20_W1)
	(setq kodBlock "LTezgah")
	(setq TK20_W1 (getreal "\nTezgahın soldan kertiğe kadar mesafesi kaç cm olsun? : "))
	(setq TK20_W2 (getreal "\nTezgahın kertik genişliği kaç cm olsun? : "))
	(setq unitW (getreal "\nTezgahın kertikten sağına kadar olam mesafesi kaç cm olsun? : "))
	(setq unitd (getreal "\nTezgah derinliği kaç cm olsun? : "))
	(setq TK20_D1 (getreal "\nKertik Derinliği kaç cm olsun? : "))
	
	(setq unitw (+ unitw TK20_W1 TK20_W2))
	(createGPanel
		(list 
			(list 0.0 0.0 0.0) 
			(list 0.0 unitD 0.0) 
			(list unitW unitD 0.0) 
			(list unitW 0.0 0.0) 
			(list (+ TK20_W1 TK20_W2) 0.0 0.0) 
			(list (+ TK20_W1 TK20_W2) TK20_D1 0.0) 
			(list TK20_W1 TK20_D1 0.0) 
			(list TK20_W1 0.0 0.0)
		) 
		nil
		3
		0.0
		;(d2r 90.0)
		0.0
		(getpoint "Köşeyi Gösteriniz:")
		"TK20_01"
		""
		nil
		"SHELF"
		kodBlock
		"CAB_DOORS"
		"noedgedrawing"		
	)
	
	(set_Mdata (entlast)  (list (cons k:mtyp "DUMMY")))
)


(setq ad_WWG-INI (strcat ad_defpath "wwg.ini"))

;Kapamaların Ölçü kontrol değerleri.
(setq kpmThickMin (cm 0.3))
(setq kpmThickMax (cm 4.0))
(setq kpmThick2Min (cm 0.6))
(setq kpmThick2Max (cm 6.0))
(setq kpmMin (cm 5.0))
(setq kpmMax (cm 365.0))

;Kapamaların kenarbandı ayarlarının yapıldığı yer.
(setq _tPay (cm 0))
(setq _45Pay (cm 0))
(setq pvckpmOn   PvcKoduON)
(setq pvckpmArka PvcKoduARKA)
(setq pvckpmAlt  PvcKoduALT)
(setq pvckpmUst  PvcKoduUST)
(setq pvckpmSag  PvcKoduYAN)
(setq pvckpmSol  PvcKoduYAN)
(setq pvckpm45  PvcKodu45)
(setq pvckpmConn  PvcKoduCONN)
(setq pvcKalinlastirmaOn  nil)
(setq pvcKalinlastirmaIc  PvcKoduGENEL)
(setq pvcKalinlastirmatPay  nil)

;WWG içinde kullanılan komutların tanımlandığı bölümdür.Modül kodlarına göre ayrı ayrı yapılmıştır ve özel reçetelerde kullanılmıştır.
;URAF Kodlu modul
(defun c:URAF_Q1 (/)
	(setq URAF_Q1 (getreal "\nKaç adet raf olsun?:"))
	(iniwrite ad_WWG-INI "URAF_settings" "URAF_Q1" (rtos URAF_Q1 2 4))
	(princ)
)

;APR1 Kodlu modul
(defun c:aprHq (/)
	(setq aprHq (getreal "\nKaç yatay bölüm olsun?:"))
	(iniwrite ad_WWG-INI "APR_settings" "aprHq" (rtos aprHq 2 4))
	(princ)
)
(defun c:aprWq (/)
	(setq aprWq (getreal "\nKaç dikey bölüm olsun?:"))
	(iniwrite ad_WWG-INI "APR_settings" "aprWq" (rtos aprWq 2 4))
	(princ)
)
(defun c:aprPq (/)
	(setq aprPq (getreal "\nProfil kalınlığı kaç cm olsun?:"))
	(iniwrite ad_WWG-INI "APR_settings" "aprPq" (rtos aprPq 2 4))
	(princ)
)
;UPR1 Kodlu modul
(defun c:uprHq (/)
	(setq uprHq (getreal "\nKaç yatay bölüm olsun?:"))
	(iniwrite ad_WWG-INI "UPR_settings" "uprHq" (rtos uprHq 2 4))
	(princ)
)
(defun c:uprWq (/)
	(setq uprWq (getreal "\nKaç dikey bölüm olsun?:"))
	(iniwrite ad_WWG-INI "UPR_settings" "uprWq" (rtos uprWq 2 4))
	(princ)
)
(defun c:uprPq (/)
	(setq uprPq (getreal "\nProfil kalınlığı kaç cm olsun?:"))
	(iniwrite ad_WWG-INI "UPR_settings" "uprPq" (rtos uprPq 2 4))
	(princ)
)
;UPR2 Kodlu modul
(defun c:upr2Hq (/)
	(setq upr2Hq (getreal "\nKaç yatay bölüm olsun?:"))
	(iniwrite ad_WWG-INI "upr2_settings" "upr2Hq" (rtos upr2Hq 2 4))
	(princ)
)
(defun c:upr2Wq (/)
	(setq upr2Wq (getreal "\nKaç dikey bölüm olsun?:"))
	(iniwrite ad_WWG-INI "upr2_settings" "upr2Wq" (rtos upr2Wq 2 4))
	(princ)
)
(defun c:upr2Pq (/)
	(setq upr2Pq (getreal "\nProfil kalınlığı kaç cm olsun?:"))
	(iniwrite ad_WWG-INI "upr2_settings" "upr2Pq" (rtos upr2Pq 2 4))
	(princ)
)
(defun c:upr2Ba (/)
	(setq upr2Ba (getreal "\nProfilli modülün alt ve üst başlangıcı kaç cm olsun?:"))
	(iniwrite ad_WWG-INI "upr2_settings" "upr2Ba" (rtos upr2Ba 2 4))
	(princ)
)
;UPR3 Kodlu modul
(defun c:upr3Hq (/)
	(setq upr3Hq (getreal "\nKaç yatay bölüm olsun?:"))
	(iniwrite ad_WWG-INI "upr3_settings" "upr3Hq" (rtos upr3Hq 2 4))
	(princ)
)
(defun c:upr3Wq (/)
	(setq upr3Wq (getreal "\nKaç dikey bölüm olsun?:"))
	(iniwrite ad_WWG-INI "upr3_settings" "upr3Wq" (rtos upr3Wq 2 4))
	(princ)
)
(defun c:upr3Pq (/)
	(setq upr3Pq (getreal "\nProfil kalınlığı kaç cm olsun?:"))
	(iniwrite ad_WWG-INI "upr3_settings" "upr3Pq" (rtos upr3Pq 2 4))
	(princ)
)
;DK20 Kodlu modul
(defun c:DK20_T1 (/)
	(setq DK20_T1 (getreal "\nPanel derinliği kaç cm olsun?:"))
	(iniwrite ad_WWG-INI "DK20_settings" "DK20_T1" (rtos DK20_T1 2 4))
	(alert "\nÖlçüsü değişen kapama modülünü yeniden yerleştirin.")
	(princ)
)
;DK30 Kodlu modul
(defun c:DK30_V2 (/)
	(setq DK30_V2 (getreal "\nPanel derinliği kaç cm olsun?:"))
	(iniwrite ad_WWG-INI "DK30_settings" "DK30_V2" (rtos DK30_V2 2 4))
	(alert "\nÖlçüsü değişen kapama modülünü yeniden yerleştirin.")
	(princ)
)
(defun c:DK30_V1 (/)
	(setq DK30_V1 (getreal "\nPanel yüksekliği kaç cm olsun?:"))
	(iniwrite ad_WWG-INI "DK30_settings" "DK30_V1" (rtos DK30_V1 2 4))
	(alert "\nÖlçüsü değişen kapama modülünü yeniden yerleştirin.")
	(princ)
)
;DT10 Kodlu modul
(defun c:DJ11_D1 (/)
	(setq DJ11_D1 (getreal "\nPanel derinliği kaç cm olsun?:"))
	(iniwrite ad_WWG-INI "DJ11_settings" "DJ11_D1" (rtos DJ11_D1 2 4))
	(alert "\nÖlçüsü değişen kapama modülünü yeniden yerleştirin.")
	(princ)
)
(defun c:DJ11_T1 (/)
		(setq DJ11_T1 (getreal "\nPanel kalinliği kaç cm olsun?:"))
	(iniwrite ad_WWG-INI "DJ11_settings" "DJ11_T1" (rtos DJ11_T1 2 4))
	(alert "\nÖlçüsü değişen kapama modülünü yeniden yerleştirin.")
	(princ)
)
;DL11 Kodlu modul
(defun c:DL11_D1 (/)
	(setq DL11_D1 (getreal "\nPanel derinliği kaç cm olsun?:"))
	(iniwrite ad_WWG-INI "DL11_settings" "DL11_D1" (rtos DL11_D1 2 4))
	(alert "\nÖlçüsü değişen kapama modülünü yeniden yerleştirin.")
	(princ)
)
(defun c:DL11_T1 (/)
	(setq DL11_T1 (getreal "\nPanel kalinliği kaç cm olsun?:"))
	(iniwrite ad_WWG-INI "DL11_settings" "DL11_T1" (rtos DL11_T1 2 4))
	(alert "\nÖlçüsü değişen kapama modülünü yeniden yerleştirin.")
	(princ)
)
;DU11 Kodlu modul
(defun c:DU11_T1 (/)
	(setq DU11_T1 (getreal "\nPanel kalinliği kaç cm olsun?:"))
	(iniwrite ad_WWG-INI "DU11_settings" "DU11_T1" (rtos DU11_T1 2 4))
	(alert "\nÖlçüsü değişen kapama modülünü yeniden yerleştirin.")
	(princ)
)
;DT11 Kodlu modul
(defun c:DT11_T1 (/)
	(setq DT11_T1 (getreal "\nPanel kalinliği kaç cm olsun?:"))
	(iniwrite ad_WWG-INI "DT11_settings" "DT11_T1" (rtos DT11_T1 2 4))
	(alert "\nÖlçüsü değişen kapama modülünü yeniden yerleştirin.")
	(princ)
)
;DC11 Kodlu modul
(defun c:DC11_T1 (/)
	(setq DC11_T1 (getreal "\nPanel kalinliği kaç cm olsun?:"))
	(iniwrite ad_WWG-INI "DC11_settings" "DC11_T1" (rtos DC11_T1 2 4))
	(alert "\nÖlçüsü değişen kapama modülünü yeniden yerleştirin.")
	(princ)
)
;DC11 Kodlu modul
(defun c:DC11_T1 (/)
	(setq DC11_T1 (getreal "\nPanel kalinliği kaç cm olsun?:"))
	(iniwrite ad_WWG-INI "DC11_settings" "DC11_T1" (rtos DC11_T1 2 4))
	(alert "\nÖlçüsü değişen kapama modülünü yeniden yerleştirin.")
	(princ)
)
;DG11 Kodlu modul
(defun c:DG11_T1 (/)
	(setq DG11_T1 (getreal "\nPanel kalinliği kaç cm olsun?:"))
	(iniwrite ad_WWG-INI "DG11_settings" "DG11_T1" (rtos DG11_T1 2 4))
	(alert "\nÖlçüsü değişen kapama modülünü yeniden yerleştirin.")
	(princ)
)
(defun c:DG11_D1 (/)
	(setq DG11_D1 (getreal "\nPanel derinliği kaç cm olsun?:"))
	(iniwrite ad_WWG-INI "DG11_settings" "DG11_D1" (rtos DG11_D1 2 4))
	(alert "\nÖlçüsü değişen kapama modülünü yeniden yerleştirin.")
	(princ)
)
(defun c:DG11_D2 (/)
	(setq DG11_D2 (getreal "\nPanel derinliği kaç cm olsun?:"))
	(iniwrite ad_WWG-INI "DG11_settings" "DG11_D2" (rtos DG11_D2 2 4))
	(alert "\nÖlçüsü değişen kapama modülünü yeniden yerleştirin.")
	(princ)
)
;DD10 Kodlu modul
(defun c:DD10_T1 (/)
	(setq DD10_T1 (getreal "\nPanel kalinliği kaç cm olsun?:"))
	(iniwrite ad_WWG-INI "DD10_settings" "DD10_T1" (rtos DD10_T1 2 4))
	(alert "\nÖlçüsü değişen kapama modülünü yeniden yerleştirin.")
	(princ)
)
;DD20 Kodlu modul
(defun c:DD20_T1 (/)
	(setq DD20_T1 (getreal "\nPanel kalinliği kaç cm olsun?:"))
	(iniwrite ad_WWG-INI "DD20_settings" "DD20_T1" (rtos DD20_T1 2 4))
	(alert "\nÖlçüsü değişen kapama modülünü yeniden yerleştirin.")
	(princ)
)
;DL10 Kodlu modul
(defun c:DL10_T1 (/)
	(setq DL10_T1 (getreal "\nPanel kalinliği kaç cm olsun?:"))
	(iniwrite ad_WWG-INI "DL10_settings" "DL10_T1" (rtos DL10_T1 2 4))
	(alert "\nÖlçüsü değişen kapama modülünü yeniden yerleştirin.")
	(princ)
)
(defun c:DL10_D1 (/)
	(setq DL10_D1 (getreal "\nPanel derinliği kaç cm olsun?:"))
	(iniwrite ad_WWG-INI "DL10_settings" "DL10_D1" (rtos DL10_D1 2 4))
	(alert "\nÖlçüsü değişen kapama modülünü yeniden yerleştirin.")
	(princ)
)
;DL20 Kodlu modul
(defun c:DL20_T1 (/)
	(setq DL20_T1 (getreal "\nPanel kalinliği kaç cm olsun?:"))
	(iniwrite ad_WWG-INI "DL20_settings" "DL20_T1" (rtos DL20_T1 2 4))
	(alert "\nÖlçüsü değişen kapama modülünü yeniden yerleştirin.")
	(princ)
)
(defun c:DL20_D1 (/)
	(setq DL20_D1 (getreal "\nPanel derinliği kaç cm olsun?:"))
	(iniwrite ad_WWG-INI "DL20_settings" "DL20_D1" (rtos DL20_D1 2 4))
	(alert "\nÖlçüsü değişen kapama modülünü yeniden yerleştirin.")
	(princ)
)
;DJ10 Kodlu modul
(defun c:DJ10_T1 (/)
	(setq DJ10_T1 (getreal "\nPanel kalinliği kaç cm olsun?:"))
	(iniwrite ad_WWG-INI "DJ10_settings" "DJ10_T1" (rtos DJ10_T1 2 4))
	(alert "\nÖlçüsü değişen kapama modülünü yeniden yerleştirin.")
	(princ)
)
(defun c:DJ10_D1 (/)
	(setq DJ10_D1 (getreal "\nPanel derinliği kaç cm olsun?:"))
	(iniwrite ad_WWG-INI "DJ10_settings" "DJ10_D1" (rtos DJ10_D1 2 4))
	(alert "\nÖlçüsü değişen kapama modülünü yeniden yerleştirin.")
	(princ)
)
;DU10 Kodlu modul
(defun c:DU10_T1 (/)
	(setq DU10_T1 (getreal "\nPanel kalinliği kaç cm olsun?:"))
	(iniwrite ad_WWG-INI "DU10_settings" "DU10_T1" (rtos DU10_T1 2 4))
	(alert "\nÖlçüsü değişen kapama modülünü yeniden yerleştirin.")
	(princ)
)
;DT10 Kodlu modul
(defun c:DT10_T1 (/)
	(setq DT10_T1 (getreal "\nPanel kalinliği kaç cm olsun?:"))
	(iniwrite ad_WWG-INI "DT10_settings" "DT10_T1" (rtos DT10_T1 2 4))
	(alert "\nÖlçüsü değişen kapama modülünü yeniden yerleştirin.")
	(princ)
)
;DG10 Kodlu modul
(defun c:DG10_T1 (/)
	(setq DG10_T1 (getreal "\nPanel kalinliği kaç cm olsun?:"))
	(iniwrite ad_WWG-INI "DG10_settings" "DG10_T1" (rtos DG10_T1 2 4))
	(alert "\nÖlçüsü değişen kapama modülünü yeniden yerleştirin.")
	(princ)
)
(defun c:DG10_D1 (/)
	(setq DG10_D1 (getreal "\nPanel derinliği kaç cm olsun?:"))
	(iniwrite ad_WWG-INI "DG10_settings" "DG10_D1" (rtos DG10_D1 2 4))
	(alert "\nÖlçüsü değişen kapama modülünü yeniden yerleştirin.")
	(princ)
)
(defun c:DG10_D2 (/)
	(setq DG10_D2 (getreal "\nPanel derinliği kaç cm olsun?:"))
	(iniwrite ad_WWG-INI "DG10_settings" "DG10_D2" (rtos DG10_D2 2 4))
	(alert "\nÖlçüsü değişen kapama modülünü yeniden yerleştirin.")
	(princ)
)
;DC10 Kodlu modul
(defun c:DC10_T1 (/)
	(setq DC10_T1 (getreal "\nPanel kalinliği kaç cm olsun?:"))
	(iniwrite ad_WWG-INI "DC10_settings" "DC10_T1" (rtos DC10_T1 2 4))
	(alert "\nÖlçüsü değişen kapama modülünü yeniden yerleştirin.")
	(princ)
)
;DK10 Kodlu modul
(defun c:DK10_T1 (/)
	(setq DK10_T1 (getreal "\nPanel kalinliği kaç cm olsun?:"))
	(iniwrite ad_WWG-INI "DK10_settings" "DK10_T1" (rtos DK10_T1 2 4))
	(alert "\nÖlçüsü değişen kapama modülünü yeniden yerleştirin.")
	(princ)
)
;DK10 Kodlu modul
(defun c:DK10_T2 (/)
	(setq DK10_T2 (getreal "\nPanel kalinliği kaç cm olsun?:"))
	(iniwrite ad_WWG-INI "DK10_settings" "DK10_T2" (rtos DK10_T2 2 4))
	(alert "\nÖlçüsü değişen kapama modülünü yeniden yerleştirin.")
	(princ)
)
;DS10 Kodlu modul
(defun c:DS10_T1 (/)
	(setq DS10_T1 (getreal "\nPanel kalinliği kaç cm olsun?:"))
	(iniwrite ad_WWG-INI "DS10_settings" "DS10_T1" (rtos DS10_T1 2 4))
	(alert "\nÖlçüsü değişen kapama modülünü yeniden yerleştirin.")
	(princ)
)
(defun c:DS10_T2 (/)
	(setq DS10_T2 (getreal "\nPanel kalinliği kaç cm olsun?:"))
	(iniwrite ad_WWG-INI "DS10_settings" "DS10_T2" (rtos DS10_T2 2 4))
	(alert "\nÖlçüsü değişen kapama modülünü yeniden yerleştirin.")
	(princ)
)
(defun c:DS10_D1 (/)
	(setq DS10_D1 (getreal "\nPanel derinliği kaç cm olsun?:"))
	(iniwrite ad_WWG-INI "DS10_settings" "DS10_D1" (rtos DS10_D1 2 4))
	(alert "\nÖlçüsü değişen kapama modülünü yeniden yerleştirin.")
	(princ)
)
(defun c:DS10_D2 (/)
	(setq DS10_D2 (getreal "\nPanel derinliği kaç cm olsun?:"))
	(iniwrite ad_WWG-INI "DS10_settings" "DS10_D2" (rtos DS10_D2 2 4))
	(alert "\nÖlçüsü değişen kapama modülünü yeniden yerleştirin.")
	(princ)
)
(defun c:DS10_D3 (/)
	(setq DS10_D3 (getreal "\nPanel derinliği kaç cm olsun?:"))
	(iniwrite ad_WWG-INI "DS10_settings" "DS10_D3" (rtos DS10_D3 2 4))
	(alert "\nÖlçüsü değişen kapama modülünü yeniden yerleştirin.")
	(princ)
)
(defun c:DS10_D4 (/)
	(setq DS10_D4 (getreal "\nPanel derinliği kaç cm olsun?:"))
	(iniwrite ad_WWG-INI "DS10_settings" "DS10_D4" (rtos DS10_D4 2 4))
	(alert "\nÖlçüsü değişen kapama modülünü yeniden yerleştirin.")
	(princ)
)
;DS20 Kodlu modul
(defun c:DS20_T1 (/)
	(setq DS20_T1 (getreal "\nPanel kalinliği kaç cm olsun?:"))
	(iniwrite ad_WWG-INI "DS20_settings" "DS20_T1" (rtos DS20_T1 2 4))
	(alert "\nÖlçüsü değişen kapama modülünü yeniden yerleştirin.")
	(princ)
)
(defun c:DS20_T2 (/)
	(setq DS20_T2 (getreal "\nPanel kalinliği kaç cm olsun?:"))
	(iniwrite ad_WWG-INI "DS20_settings" "DS20_T2" (rtos DS20_T2 2 4))
	(alert "\nÖlçüsü değişen kapama modülünü yeniden yerleştirin.")
	(princ)
)
(defun c:DS20_D1 (/)
	(setq DS20_D1 (getreal "\nPanel derinliği kaç cm olsun?:"))
	(iniwrite ad_WWG-INI "DS20_settings" "DS20_D1" (rtos DS20_D1 2 4))
	(alert "\nÖlçüsü değişen kapama modülünü yeniden yerleştirin.")
	(princ)
)
;DS30 Kodlu modul
(defun c:DS30_T1 (/)
	(setq DS30_T1 (getreal "\nPanel kalinliği kaç cm olsun?:"))
	(iniwrite ad_WWG-INI "DS30_settings" "DS30_T1" (rtos DS30_T1 2 4))
	(alert "\nÖlçüsü değişen kapama modülünü yeniden yerleştirin.")
	(princ)
)
(defun c:DS30_T2 (/)
	(setq DS30_T2 (getreal "\nPanel kalinliği kaç cm olsun?:"))
	(iniwrite ad_WWG-INI "DS30_settings" "DS30_T2" (rtos DS30_T2 2 4))
	(alert "\nÖlçüsü değişen kapama modülünü yeniden yerleştirin.")
	(princ)
)
(defun c:DS30_D1 (/)
	(setq DS30_D1 (getreal "\nPanel derinliği kaç cm olsun?:"))
	(iniwrite ad_WWG-INI "DS30_settings" "DS30_D1" (rtos DS30_D1 2 4))
	(alert "\nÖlçüsü değişen kapama modülünü yeniden yerleştirin.")
	(princ)
)
(defun c:DS30_D2 (/)
	(setq DS30_D2 (getreal "\nPanel derinliği kaç cm olsun?:"))
	(iniwrite ad_WWG-INI "DS30_settings" "DS30_D2" (rtos DS30_D2 2 4))
	(alert "\nÖlçüsü değişen kapama modülünü yeniden yerleştirin.")
	(princ)
)
;DS40 Kodlu modul
(defun c:DS40_T1 (/)
	(setq DS40_T1 (getreal "\nPanel kalinliği kaç cm olsun?:"))
	(iniwrite ad_WWG-INI "DS40_settings" "DS40_T1" (rtos DS40_T1 2 4))
	(alert "\nÖlçüsü değişen kapama modülünü yeniden yerleştirin.")
	(princ)
)
(defun c:DS40_T2 (/)
	(setq DS40_T2 (getreal "\nPanel kalinliği kaç cm olsun?:"))
	(iniwrite ad_WWG-INI "DS40_settings" "DS40_T2" (rtos DS40_T2 2 4))
	(alert "\nÖlçüsü değişen kapama modülünü yeniden yerleştirin.")
	(princ)
)
(defun c:DS40_D1 (/)
	(setq DS40_D1 (getreal "\nPanel derinliği kaç cm olsun?:"))
	(iniwrite ad_WWG-INI "DS40_settings" "DS40_D1" (rtos DS40_D1 2 4))
	(alert "\nÖlçüsü değişen kapama modülünü yeniden yerleştirin.")
	(princ)
)
(defun c:DS40_D2 (/)
	(setq DS40_D2 (getreal "\nPanel derinliği kaç cm olsun?:"))
	(iniwrite ad_WWG-INI "DS40_settings" "DS40_D2" (rtos DS40_D2 2 4))
	(alert "\nÖlçüsü değişen kapama modülünü yeniden yerleştirin.")
	(princ)
)
;YL11 Kodlu modul
(defun c:YL11_T1 (/)
	(setq YL11_T1 (getreal "\nPanel kalinliği kaç cm olsun?:"))
	(iniwrite ad_WWG-INI "YL11_settings" "YL11_T1" (rtos YL11_T1 2 4))
	(alert "\nÖlçüsü değişen kapama modülünü yeniden yerleştirin.")
	(princ)
)
(defun c:YL11_D1 (/)
	(setq YL11_D1 (getreal "\nPanel derinliği kaç cm olsun?:"))
	(iniwrite ad_WWG-INI "YL11_settings" "YL11_D1" (rtos YL11_D1 2 4))
	(alert "\nÖlçüsü değişen kapama modülünü yeniden yerleştirin.")
	(princ)
)
;YU11 Kodlu modul
(defun c:YU11_T1 (/)
	(setq YU11_T1 (getreal "\nPanel kalinliği kaç cm olsun?:"))
	(iniwrite ad_WWG-INI "YU11_settings" "YU11_T1" (rtos YU11_T1 2 4))
	(alert "\nÖlçüsü değişen kapama modülünü yeniden yerleştirin.")
	(princ)
)
;YJ11 Kodlu modul
(defun c:YJ11_T1 (/)
	(setq YJ11_T1 (getreal "\nPanel kalinliği kaç cm olsun?:"))
	(iniwrite ad_WWG-INI "YJ11_settings" "YJ11_T1" (rtos YJ11_T1 2 4))
	(alert "\nÖlçüsü değişen kapama modülünü yeniden yerleştirin.")
	(princ)
)
(defun c:YJ11_D1 (/)
	(setq YJ11_D1 (getreal "\nPanel derinliği kaç cm olsun?:"))
	(iniwrite ad_WWG-INI "YJ11_settings" "YJ11_D1" (rtos YJ11_D1 2 4))
	(alert "\nÖlçüsü değişen kapama modülünü yeniden yerleştirin.")
	(princ)
)
;YT11 Kodlu modul
(defun c:YT11_T1 (/)
	(setq YT11_T1 (getreal "\nPanel kalinliği kaç cm olsun?:"))
	(iniwrite ad_WWG-INI "YT11_settings" "YT11_T1" (rtos YT11_T1 2 4))
	(alert "\nÖlçüsü değişen kapama modülünü yeniden yerleştirin.")
	(princ)
)
;YC11 Kodlu modul
(defun c:YC11_T1 (/)
	(setq YC11_T1 (getreal "\nPanel kalinliği kaç cm olsun?:"))
	(iniwrite ad_WWG-INI "YC11_settings" "YC11_T1" (rtos YC11_T1 2 4))
	(alert "\nÖlçüsü değişen kapama modülünü yeniden yerleştirin.")
	(princ)
)
;YG11 Kodlu modul
(defun c:YG11_T1 (/)
	(setq YG11_T1 (getreal "\nPanel kalinliği kaç cm olsun?:"))
	(iniwrite ad_WWG-INI "YG11_settings" "YG11_T1" (rtos YG11_T1 2 4))
	(alert "\nÖlçüsü değişen kapama modülünü yeniden yerleştirin.")
	(princ)
)
(defun c:YG11_D1 (/)
	(setq YG11_D1 (getreal "\nPanel derinliği kaç cm olsun?:"))
	(iniwrite ad_WWG-INI "YG11_settings" "YG11_D1" (rtos YG11_D1 2 4))
	(alert "\nÖlçüsü değişen kapama modülünü yeniden yerleştirin.")
	(princ)
)
(defun c:YG11_D2 (/)
	(setq YG11_D2 (getreal "\nPanel derinliği kaç cm olsun?:"))
	(iniwrite ad_WWG-INI "YG11_settings" "YG11_D2" (rtos YG11_D2 2 4))
	(alert "\nÖlçüsü değişen kapama modülünü yeniden yerleştirin.")
	(princ)
)
;YL10 Kodlu modul
(defun c:YL10_T1 (/)
	(setq YL10_T1 (getreal "\nPanel kalinliği kaç cm olsun?:"))
	(iniwrite ad_WWG-INI "YL10_settings" "YL10_T1" (rtos YL10_T1 2 4))
	(alert "\nÖlçüsü değişen kapama modülünü yeniden yerleştirin.")
	(princ)
)
(defun c:YL10_D1 (/)
	(setq YL10_D1 (getreal "\nPanel derinliği kaç cm olsun?:"))
	(iniwrite ad_WWG-INI "YL10_settings" "YL10_D1" (rtos YL10_D1 2 4))
	(alert "\nÖlçüsü değişen kapama modülünü yeniden yerleştirin.")
	(princ)
)
;YR10 Kodlu modul
(defun c:YR10_T1 (/)
	(setq YR10_T1 (getreal "\nPanel kalinliği kaç cm olsun?:"))
	(iniwrite ad_WWG-INI "YR10_settings" "YR10_T1" (rtos YR10_T1 2 4))
	(alert "\nÖlçüsü değişen kapama modülünü yeniden yerleştirin.")
	(princ)
)
(defun c:YR10_T2 (/)
	(setq YR10_T2 (getreal "\nPanel kalinliği kaç cm olsun?:"))
	(iniwrite ad_WWG-INI "YR10_settings" "YR10_T2" (rtos YR10_T2 2 4))
	(alert "\nÖlçüsü değişen kapama modülünü yeniden yerleştirin.")
	(princ)
)
(defun c:YR10_D1 (/)
	(setq YR10_D1 (getreal "\nPanel derinliği kaç cm olsun?:"))
	(iniwrite ad_WWG-INI "YR10_settings" "YR10_D1" (rtos YR10_D1 2 4))
	(alert "\nÖlçüsü değişen kapama modülünü yeniden yerleştirin.")
	(princ)
)
(defun c:YR10_H1 (/)
	(setq YR10_H1 (getreal "\nAlt mesafa kaç cm olsun?:"))
	(iniwrite ad_WWG-INI "YR10_settings" "YR10_H1" (rtos YR10_H1 2 4))
	(alert "\nÖlçüsü değişen kapama modülünü yeniden yerleştirin.")
	(princ)
)

;YU10 Kodlu modul
(defun c:YU10_T1 (/)
	(setq YU10_T1 (getreal "\nPanel kalinliği kaç cm olsun?:"))
	(iniwrite ad_WWG-INI "YU10_settings" "YU10_T1" (rtos YU10_T1 2 4))
	(alert "\nÖlçüsü değişen kapama modülünü yeniden yerleştirin.")
	(princ)
)
;YJ10 Kodlu modul
(defun c:YJ10_T1 (/)
	(setq YJ10_T1 (getreal "\nPanel kalinliği kaç cm olsun?:"))
	(iniwrite ad_WWG-INI "YJ10_settings" "YJ10_T1" (rtos YJ10_T1 2 4))
	(alert "\nÖlçüsü değişen kapama modülünü yeniden yerleştirin.")
	(princ)
)
(defun c:YJ10_D1 (/)
	(setq YJ10_D1 (getreal "\nPanel derinliği kaç cm olsun?:"))
	(iniwrite ad_WWG-INI "YJ10_settings" "YJ10_D1" (rtos YJ10_D1 2 4))
	(alert "\nÖlçüsü değişen kapama modülünü yeniden yerleştirin.")
	(princ)
)
;YT10 Kodlu modul
(defun c:YT10_T1 (/)
	(setq YT10_T1 (getreal "\nPanel kalinliği kaç cm olsun?:"))
	(iniwrite ad_WWG-INI "YT10_settings" "YT10_T1" (rtos YT10_T1 2 4))
	(alert "\nÖlçüsü değişen kapama modülünü yeniden yerleştirin.")
	(princ)
)
;YC10 Kodlu modul
(defun c:YC10_T1 (/)
	(setq YC10_T1 (getreal "\nPanel kalinliği kaç cm olsun?:"))
	(iniwrite ad_WWG-INI "YC10_settings" "YC10_T1" (rtos YC10_T1 2 4))
	(alert "\nÖlçüsü değişen kapama modülünü yeniden yerleştirin.")
	(princ)
)
;YG10 Kodlu modul
(defun c:YG10_T1 (/)
	(setq YG10_T1 (getreal "\nPanel kalinliği kaç cm olsun?:"))
	(iniwrite ad_WWG-INI "YG10_settings" "YG10_T1" (rtos YG10_T1 2 4))
	(alert "\nÖlçüsü değişen kapama modülünü yeniden yerleştirin.")
	(princ)
)
(defun c:YG10_D1 (/)
	(setq YG10_D1 (getreal "\nPanel derinliği kaç cm olsun?:"))
	(iniwrite ad_WWG-INI "YG10_settings" "YG10_D1" (rtos YG10_D1 2 4))
	(alert "\nÖlçüsü değişen kapama modülünü yeniden yerleştirin.")
	(princ)
)
(defun c:YG10_D2 (/)
	(setq YG10_D2 (getreal "\nPanel derinliği kaç cm olsun?:"))
	(iniwrite ad_WWG-INI "YG10_settings" "YG10_D2" (rtos YG10_D2 2 4))
	(alert "\nÖlçüsü değişen kapama modülünü yeniden yerleştirin.")
	(princ)
)
;YK10 Kodlu modul
(defun c:YK10_T1 (/)
	(setq YK10_T1 (getreal "\nPanel kalinliği kaç cm olsun?:"))
	(iniwrite ad_WWG-INI "YK10_settings" "YK10_T1" (rtos YK10_T1 2 4))
	(alert "\nÖlçüsü değişen kapama modülünü yeniden yerleştirin.")
	(princ)
)
(defun c:YK10_T2 (/)
	(setq YK10_T2 (getreal "\nPanel kalinliği kaç cm olsun?:"))
	(iniwrite ad_WWG-INI "YK10_settings" "YK10_T2" (rtos YK10_T2 2 4))
	(alert "\nÖlçüsü değişen kapama modülünü yeniden yerleştirin.")
	(princ)
)
;YS10 Kodlu modul
(defun c:YS10_T1 (/)
	(setq YS10_T1 (getreal "\nPanel kalinliği kaç cm olsun?:"))
	(iniwrite ad_WWG-INI "YS10_settings" "YS10_T1" (rtos YS10_T1 2 4))
	(alert "\nÖlçüsü değişen kapama modülünü yeniden yerleştirin.")
	(princ)
)
(defun c:YS10_T2 (/)
	(setq YS10_T2 (getreal "\nPanel kalinliği kaç cm olsun?:"))
	(iniwrite ad_WWG-INI "YS10_settings" "YS10_T2" (rtos YS10_T2 2 4))
	(alert "\nÖlçüsü değişen kapama modülünü yeniden yerleştirin.")
	(princ)
)
(defun c:YS10_D1 (/)
	(setq YS10_D1 (getreal "\nPanel derinliği kaç cm olsun?:"))
	(iniwrite ad_WWG-INI "YS10_settings" "YS10_D1" (rtos YS10_D1 2 4))
	(alert "\nÖlçüsü değişen kapama modülünü yeniden yerleştirin.")
	(princ)
)
(defun c:YS10_D2 (/)
	(setq YS10_D2 (getreal "\nPanel derinliği kaç cm olsun?:"))
	(iniwrite ad_WWG-INI "YS10_settings" "YS10_D2" (rtos YS10_D2 2 4))
	(alert "\nÖlçüsü değişen kapama modülünü yeniden yerleştirin.")
	(princ)
)
(defun c:YS10_D3 (/)
	(setq YS10_D3 (getreal "\nPanel derinliği kaç cm olsun?:"))
	(iniwrite ad_WWG-INI "YS10_settings" "YS10_D3" (rtos YS10_D3 2 4))
	(alert "\nÖlçüsü değişen kapama modülünü yeniden yerleştirin.")
	(princ)
)
(defun c:YS10_D4 (/)
	(setq YS10_D4 (getreal "\nPanel derinliği kaç cm olsun?:"))
	(iniwrite ad_WWG-INI "YS10_settings" "YS10_D4" (rtos YS10_D4 2 4))
	(alert "\nÖlçüsü değişen kapama modülünü yeniden yerleştirin.")
	(princ)
)
;YS20 Kodlu modul
(defun c:YS20_T1 (/)
	(setq YS20_T1 (getreal "\nPanel kalinliği kaç cm olsun?:"))
	(iniwrite ad_WWG-INI "YS20_settings" "YS20_T1" (rtos YS20_T1 2 4))
	(alert "\nÖlçüsü değişen kapama modülünü yeniden yerleştirin.")
	(princ)
)
(defun c:YS20_T2 (/)
	(setq YS20_T2 (getreal "\nPanel kalinliği kaç cm olsun?:"))
	(iniwrite ad_WWG-INI "YS20_settings" "YS20_T2" (rtos YS20_T2 2 4))
	(alert "\nÖlçüsü değişen kapama modülünü yeniden yerleştirin.")
	(princ)
)
(defun c:YS20_D1 (/)
	(setq YS20_D1 (getreal "\nPanel derinliği kaç cm olsun?:"))
	(iniwrite ad_WWG-INI "YS20_settings" "YS20_D1" (rtos YS20_D1 2 4))
	(alert "\nÖlçüsü değişen kapama modülünü yeniden yerleştirin.")
	(princ)
)

;CT10 Kodlu modul
(defun c:CT10_T1 (/)
	(setq CT10_T1 (getreal "\nPanel kalinliği kaç cm olsun?:"))
	(iniwrite ad_WWG-INI "CT10_settings" "CT10_T1" (rtos CT10_T1 2 4))
	(alert "\nÖlçüsü değişen kapama modülünü yeniden yerleştirin.")
	(princ)
)
(defun c:CT10_T2 (/)
	(setq CT10_T2 (getreal "\nPanel kalinliği kaç cm olsun?:"))
	(iniwrite ad_WWG-INI "CT10_settings" "CT10_T2" (rtos CT10_T2 2 4))
	(alert "\nÖlçüsü değişen kapama modülünü yeniden yerleştirin.")
	(princ)
)

;KR10 Kodlu modul
(defun c:KR10_T1 (/)
	(setq KR10_T1 (getreal "\nPanel kalinliği kaç cm olsun?:"))
	(iniwrite ad_WWG-INI "KR10_settings" "KR10_T1" (rtos KR10_T1 2 4))
	(alert "\nÖlçüsü değişen kapama modülünü yeniden yerleştirin.")
	(princ)
)
(defun c:KR10_D1 (/)
	(setq KR10_D1 (getreal "\nPanel derinliği kaç cm olsun?:"))
	(iniwrite ad_WWG-INI "KR10_settings" "KR10_D1" (rtos KR10_D1 2 4))
	(alert "\nÖlçüsü değişen kapama modülünü yeniden yerleştirin.")
	(princ)
)
;KR20 Kodlu modul
(defun c:KR20_T1 (/)
	(setq KR20_T1 (getreal "\nPanel kalinliği kaç cm olsun?:"))
	(iniwrite ad_WWG-INI "KR20_settings" "KR20_T1" (rtos KR20_T1 2 4))
	(alert "\nÖlçüsü değişen kapama modülünü yeniden yerleştirin.")
	(princ)
)


(setq DJ11_D1	(atof (iniread ad_WWG-INI "DJ11_settings"	"DJ11_D1"		"1.8" )))
(setq DJ11_T1	(atof (iniread ad_WWG-INI "DJ11_settings"	"DJ11_T1"		"1.8" )))
(setq DL11_D1	(atof (iniread ad_WWG-INI "DL11_settings"	"DL11_D1"		"1.8" )))
(setq DL11_T1	(atof (iniread ad_WWG-INI "DL11_settings"	"DL11_T1"		"1.8" )))
(setq DU11_T1	(atof (iniread ad_WWG-INI "DU11_settings"	"DU11_T1"		"1.8" )))
(setq DT11_T1	(atof (iniread ad_WWG-INI "DT11_settings"	"DT11_T1"		"1.8" )))
(setq DC11_T1	(atof (iniread ad_WWG-INI "DC11_settings"	"DC11_T1"		"1.8" )))
(setq DG11_D1	(atof (iniread ad_WWG-INI "DG11_settings"	"DG11_D1"		"1.8" )))
(setq DG11_D2	(atof (iniread ad_WWG-INI "DG11_settings"	"DG11_D2"		"1.8" )))
(setq DG11_T1	(atof (iniread ad_WWG-INI "DG11_settings"	"DG11_T1"		"1.8" )))
(setq DD10_T1	(atof (iniread ad_WWG-INI "DD10_settings"	"DD10_T1"		"1.8" )))
(setq DD20_T1	(atof (iniread ad_WWG-INI "DD20_settings"	"DD20_T1"		"1.8" )))
(setq DL10_T1	(atof (iniread ad_WWG-INI "DL10_settings"	"DL10_T1"		"1.8" )))
(setq DL20_T1	(atof (iniread ad_WWG-INI "DL20_settings"	"DL20_T1"		"1.8" )))
(setq DL20_D1	(atof (iniread ad_WWG-INI "DL20_settings"	"DL20_D1"		"1.8" )))
(setq DL10_D1	(atof (iniread ad_WWG-INI "DL10_settings"	"DL10_D1"		"1.8" )))
(setq DJ10_T1	(atof (iniread ad_WWG-INI "DJ10_settings"	"DJ10_T1"		"1.8" )))
(setq DJ10_D1	(atof (iniread ad_WWG-INI "DJ10_settings"	"DJ10_D1"		"1.8" )))
(setq DU10_T1	(atof (iniread ad_WWG-INI "DU10_settings"	"DU10_T1"		"1.8" )))
(setq DT10_T1	(atof (iniread ad_WWG-INI "DT10_settings"	"DT10_T1"		"1.8" )))
(setq DG10_T1	(atof (iniread ad_WWG-INI "DG10_settings"	"DG10_T1"		"1.8" )))
(setq DG10_D1	(atof (iniread ad_WWG-INI "DG10_settings"	"DG10_D1"		"1.8" )))
(setq DG10_D2	(atof (iniread ad_WWG-INI "DG10_settings"	"DG10_D2"		"1.8" )))
(setq DC10_T1	(atof (iniread ad_WWG-INI "DC10_settings"	"DC10_T1"		"1.8" )))
(setq DK10_T1	(atof (iniread ad_WWG-INI "DK10_settings"	"DK10_T1"		"1.8" )))
(setq DK10_T2	(atof (iniread ad_WWG-INI "DK10_settings"	"DK10_T2"		"1.8" )))
(setq DK30_V2	(atof (iniread ad_WWG-INI "DK30_settings"	"DK30_V2"		"1.8" )))
(setq DK30_V1	(atof (iniread ad_WWG-INI "DK30_settings"	"DK30_V1"		"1.8" )))
(setq DS10_T1	(atof (iniread ad_WWG-INI "DS10_settings"	"DS10_T1"		"1.8" )))
(setq DS10_T2	(atof (iniread ad_WWG-INI "DS10_settings"	"DS10_T2"		"1.8" )))
(setq DS10_D1	(atof (iniread ad_WWG-INI "DS10_settings"	"DS10_D1"		"1.8" )))
(setq DS10_D2	(atof (iniread ad_WWG-INI "DS10_settings"	"DS10_D2"		"1.8" )))
(setq DS10_D3	(atof (iniread ad_WWG-INI "DS10_settings"	"DS10_D3"		"1.8" )))
(setq DS10_D4	(atof (iniread ad_WWG-INI "DS10_settings"	"DS10_D4"		"1.8" )))
(setq DS20_T1	(atof (iniread ad_WWG-INI "DS20_settings"	"DS20_T1"		"1.8" )))
(setq DS20_T2	(atof (iniread ad_WWG-INI "DS20_settings"	"DS20_T2"		"1.8" )))
(setq DS20_D1	(atof (iniread ad_WWG-INI "DS20_settings"	"DS20_D1"		"1.8" )))
(setq DS30_T1	(atof (iniread ad_WWG-INI "DS30_settings"	"DS30_T1"		"1.8" )))
(setq DS30_T2	(atof (iniread ad_WWG-INI "DS30_settings"	"DS30_T2"		"1.8" )))
(setq DS30_D1	(atof (iniread ad_WWG-INI "DS30_settings"	"DS30_D1"		"1.8" )))
(setq DS30_D2	(atof (iniread ad_WWG-INI "DS30_settings"	"DS30_D2"		"1.8" )))
(setq DS40_T1	(atof (iniread ad_WWG-INI "DS40_settings"	"DS40_T1"		"1.8" )))
(setq DS40_T2	(atof (iniread ad_WWG-INI "DS40_settings"	"DS40_T2"		"1.8" )))
(setq DS40_D1	(atof (iniread ad_WWG-INI "DS40_settings"	"DS40_D1"		"1.8" )))
(setq DS40_D2	(atof (iniread ad_WWG-INI "DS40_settings"	"DS40_D2"		"1.8" )))
(setq YL11_T1	(atof (iniread ad_WWG-INI "YL11_settings"	"YL11_T1"		"1.8" )))
(setq YL11_D1	(atof (iniread ad_WWG-INI "YL11_settings"	"YL11_D1"		"1.8" )))
(setq YU11_T1	(atof (iniread ad_WWG-INI "YU11_settings"	"YU11_T1"		"1.8" )))
(setq YJ11_T1	(atof (iniread ad_WWG-INI "YJ11_settings"	"YJ11_T1"		"1.8" )))
(setq YJ11_D1	(atof (iniread ad_WWG-INI "YJ11_settings"	"YJ11_D1"		"1.8" )))
(setq YT11_T1	(atof (iniread ad_WWG-INI "YT11_settings"	"YT11_T1"		"1.8" )))
(setq YC11_T1	(atof (iniread ad_WWG-INI "YC11_settings"	"YC11_T1"		"1.8" )))
(setq YG11_T1	(atof (iniread ad_WWG-INI "YG11_settings"	"YG11_T1"		"1.8" )))
(setq YG11_D1	(atof (iniread ad_WWG-INI "YG11_settings"	"YG11_D1"		"1.8" )))
(setq YG11_D2	(atof (iniread ad_WWG-INI "YG11_settings"	"YG11_D2"		"1.8" )))
(setq YL10_T1	(atof (iniread ad_WWG-INI "YL10_settings"	"YL10_T1"		"1.8" )))
(setq YL10_D1	(atof (iniread ad_WWG-INI "YL10_settings"	"YL10_D1"		"1.8" )))
(setq YR10_T1	(atof (iniread ad_WWG-INI "YR10_settings"	"YR10_T1"		"1.8" )))
(setq YR10_T2	(atof (iniread ad_WWG-INI "YR10_settings"	"YR10_T2"		"1.8" )))
(setq YR10_D1	(atof (iniread ad_WWG-INI "YR10_settings"	"YR10_D1"		"1.8" )))
(setq YR10_H1	(atof (iniread ad_WWG-INI "YR10_settings"	"YR10_H1"		"1.8" )))
(setq YU10_T1	(atof (iniread ad_WWG-INI "YU10_settings"	"YU10_T1"		"1.8" )))
(setq YJ10_D1	(atof (iniread ad_WWG-INI "YJ10_settings"	"YJ10_D1"		"1.8" )))
(setq YT10_T1	(atof (iniread ad_WWG-INI "YT10_settings"	"YT10_T1"		"1.8" )))
(setq YJ10_T1	(atof (iniread ad_WWG-INI "YJ10_settings"	"YJ10_T1"		"1.8" )))
(setq YC10_T1	(atof (iniread ad_WWG-INI "YC10_settings"	"YC10_T1"		"1.8" )))
(setq YG10_D1	(atof (iniread ad_WWG-INI "YG10_settings"	"YG10_D1"		"1.8" )))
(setq YG10_D2	(atof (iniread ad_WWG-INI "YG10_settings"	"YG10_D2"		"1.8" )))
(setq YG10_T1	(atof (iniread ad_WWG-INI "YG10_settings"	"YG10_T1"		"1.8" )))
(setq YK10_T1	(atof (iniread ad_WWG-INI "YK10_settings"	"YK10_T1"		"1.8" )))
(setq YK10_T2	(atof (iniread ad_WWG-INI "YK10_settings"	"YK10_T2"		"1.8" )))
(setq YS10_T1	(atof (iniread ad_WWG-INI "YS10_settings"	"YS10_T1"		"1.8" )))
(setq YS10_T2	(atof (iniread ad_WWG-INI "YS10_settings"	"YS10_T2"		"1.8" )))
(setq YS10_D1	(atof (iniread ad_WWG-INI "YS10_settings"	"YS10_D1"		"1.8" )))
(setq YS10_D2	(atof (iniread ad_WWG-INI "YS10_settings"	"YS10_D2"		"1.8" )))
(setq YS10_D3	(atof (iniread ad_WWG-INI "YS10_settings"	"YS10_D3"		"1.8" )))
(setq YS10_D4	(atof (iniread ad_WWG-INI "YS10_settings"	"YS10_D4"		"1.8" )))
(setq YS20_T1	(atof (iniread ad_WWG-INI "YS20_settings"	"YS20_T1"		"1.8" )))
(setq YS20_T2	(atof (iniread ad_WWG-INI "YS20_settings"	"YS20_T2"		"1.8" )))
(setq YS20_D1	(atof (iniread ad_WWG-INI "YS20_settings"	"YS20_D1"		"1.8" )))
(setq DK20_T1	(atof (iniread ad_WWG-INI "DK20_settings"	"DK20_T1"		"1.8" )))
(setq CT10_T1	(atof (iniread ad_WWG-INI "CT10_settings"	"CT10_T1"		"1.8" )))
(setq CT10_T2	(atof (iniread ad_WWG-INI "CT10_settings"	"CT10_T2"		"1.8" )))
(setq KR10_T1	(atof (iniread ad_WWG-INI "KR10_settings"	"KR10_T1"		"1.8" )))
(setq KR20_T1	(atof (iniread ad_WWG-INI "KR20_settings"	"KR20_T1"		"1.8" )))
(setq URAF_Q1	(atof (iniread ad_WWG-INI "URAF_settings"	"URAF_Q1"		"1.8" )))
(setq aprHq		(atof (iniread ad_WWG-INI "APR_settings"	"aprHq"			"2" )))
(setq aprWq		(atof (iniread ad_WWG-INI "APR_settings"	"aprWq"			"2" )))
(setq aprPq		(atof (iniread ad_WWG-INI "APR_settings"	"aprPq"			"2" )))
(setq uprHq		(atof (iniread ad_WWG-INI "UPR_settings"	"uprHq"			"2" )))
(setq uprWq		(atof (iniread ad_WWG-INI "UPR_settings"	"uprWq"			"2" )))
(setq uprPq		(atof (iniread ad_WWG-INI "UPR_settings"	"uprPq"			"2" )))
(setq upr2Hq	(atof (iniread ad_WWG-INI "UPR2_settings"	"upr2Hq"		"2" )))
(setq upr2Wq	(atof (iniread ad_WWG-INI "UPR2_settings"	"upr2Wq"		"2" )))
(setq upr2Pq	(atof (iniread ad_WWG-INI "UPR2_settings"	"upr2Pq"		"2" )))
(setq upr2Ba	(atof (iniread ad_WWG-INI "UPR2_settings"	"upr2Ba"		"2" )))
(setq upr3Hq	(atof (iniread ad_WWG-INI "UPR3_settings"	"upr3Hq"		"2" )))
(setq upr3Wq	(atof (iniread ad_WWG-INI "UPR3_settings"	"upr3Wq"		"2" )))
(setq upr3Pq	(atof (iniread ad_WWG-INI "UPR3_settings"	"upr3Pq"		"2" )))
